submodule Device.DeviceInfo.SupportedDataModel {

    belongs-to "Device.DeviceInfo" {prefix "Device.DeviceInfo";}

    yang-version 1;

    import ietf-inet-types {prefix inet;}

    organization "Deutsche Telekom AG";

    contact 
        'Web:   <http://opencpe.org/contact>
Email: OpenCPE Support
       <mailto:support@opencpe.org>';

    description
        'Copyright (c) 2013 Deutsche Telekom AG

This module is the DeviceInfo.SupportedDataModel branch of the Device:2 Datamodel for TR-069/WT-181.
';

    revision "2013-09-22" {
        description "Version 0.1.0 -- Initial release";
    }

    grouping SupportedDataModel {
        list SupportedDataModel {
            config false;
            description "This table contains details of the device's
                Current Supported Data Model.
                The table MUST describe the device's entire Supported Data Model.
                Therefore, if a device's Supported Data Model changes at run-time,
                entries will need to be added or removed as appropriate.
                    Each table entry MUST refer to only a single Root Object or Service
                    Object. The device MAY choose to use more than one table entry for a
                    given Root Object or Service Object.
                    Considering that every device has some form of a data model, this table
                    MUST NOT be empty.
                    At most one entry in this table can exist with a given value for URL.";

            key "URL";

            leaf URL {
                // defined as string in WT181i2
                type inet:uri {
                    length 256;
                }
                config false;
                description "URL ([RFC3986]) that describes some or all of
                    the device's Current Supported Data Model.
                    The URL MUST reference an XML file which describes the appropriate part
                    of the Supported Data Model.
                    The referenced XML file MUST be compliant with the DT (Device Type)
                    Schema that is described in [TR-106a3] Annex B, including any
                    additional normative requirements referenced within the Schema.
                    The XML file referenced by this URL MUST NOT change while the CPE is
                    running, and SHOULD NOT change across a CPE reboot. Note that, if the
                    same XML file is to be used for multiple CPE, this strongly suggests
                    that the XML file referenced by this URL should never change.
                    The URL MAY permit the XML file to be accessed at run-time, in which
                    case, the XML file MAY be located within the CPE.
                    Behavior in the event of an invalid URL, failure to access the
                    referenced XML file, or an invalid XML file, is
                    implementation-dependent.";
                reference "RFC3986, TR-106a3 Annex B";
            }

            leaf URN {
                type string {
                    length 256;
                }
                config false;
                description "URN ([RFC3986]) that is the value of the spec
                    attribute in the DM (data model) Instance that defines the Root Object
                    or Service Object referenced by this table entry.
                    For example, if this table entry references a DT Instance that refers
                    to the Device:1.3 Root Object, the value of this parameter would be
                    urn:broadband-forum-org:tr-157-1-0-0, because TR-157 defines
                    Device:1.3. If the DT Instance instead referred to a vendor-specific
                    Root Object, e.g. X_EXAMPLE_Device:1.0 (derived from Device:1.3), the
                    value of this parameter would be something like
                    urn:example-com:device-1-0-0.";
                reference "RFC3986";
            }

            leaf-list Feature {
                type string;
                config false;
                description "This parameter MUST list exactly the features
                    that are defined using the top-level feature element in the DT Instance
                    referenced by URL.
                    For example, if the DT instance specified the following:
                    <feature name='DNSServer'/>
                    <feature name='Router'/>
                    <feature name='X_MyDeviceFeature'/>
                    then the value of this parameter might be DNSServer,Router,
                         X_MyDeviceFeature. The order in which the features are listed is not
                             significant.";
            }

        } // list SupportedDataModel
    } // grouping SupportedDataModel
} // module
