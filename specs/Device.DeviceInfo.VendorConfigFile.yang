submodule Device.DeviceInfo.VendorConfigFile {

    belongs-to "Device.DeviceInfo" {prefix "Device.DeviceInfo";}

    yang-version 1;

    import ietf-yang-types {prefix yang;}

    organization "Deutsche Telekom AG";

    contact 
        'Web:   <http://opencpe.org/contact>
Email: OpenCPE Support
       <mailto:support@opencpe.org>';

    description
        'Copyright (c) 2013 Deutsche Telekom AG

This module is the DeviceInfo.VendorConfigFile branch of the Device:2 Datamodel for TR-069/WT-181.
';

    revision "2013-09-22" {
        description "Version 0.1.0 -- Initial release";
    }

    grouping VendorConfigFile {
        list VendorConfigFile {
            description "Every instance of this object is a Vendor
                Configuration File, and contains parameters associated with the Vendor
                Configuration File.
                This table of Vendor Configuration Files is for information only and
                does not allow the ACS to operate on these files in any way.
                Whenever the CPE successfully downloads a configuration file as a
                result of the Download RPC with the FileType argument of 3 Vendor
                Configuration File, the CPE MUST update this table. If the name of the
                file (determined as described in the definition of the Name parameter)
                differs from that of any existing instance, then the CPE MUST create a
                new instance to represent this file. If instead, the name of the file
                is identical to that of an existing instance, then the CPE MUST update
                the content of the existing instance with the new version, date, and
                (optionally) description of the file.";

            key "Alias";

            leaf Alias {
                type string {
                    length "0..64";
                }
                config true;
                description "A non-functional key used to identify this table
                    entry. Alias MUST be unique across all instances of
                    Device.DeviceInfo.VendorConfigFile.{i}.  irrespective of values of any
                    other parameter. An initial unique value MUST be assigned when the CPE
                    creates an instance of this object. The ACS MAY later assign a
                    different unique value if desired.";
            }

            leaf Name {
                type string {
                    length "0..64";
                }
                config false;
                description "Name of the vendor configuration file.
                    If the CPE is able to obtain the name of the configuration file from
                    the file itself, then the value of this parameter MUST be set to that
                    name.
                    Otherwise, if the CPE can extract the file name from the URL used to
                    download the configuration file, then the value of this parameter MUST
                    be set to that name.
                    Otherwise, the value of this parameter MUST be set to the value of the
                    TargetFileName argument of the Download RPC used to download this
                    configuration file.";
            }

            leaf Version {
                type string {
                    length "0..16";
                }
                config false;
                description "A string identifying the configuration file
                    version currently used in the CPE.
                    If the CPE is able to obtain the version of the configuration file from
                    the file itself, then the value of this parameter MUST be set to the
                    obtained value.
                    Otherwise, the value of this parameter MUST be an empty string.";
            }

            leaf Date {
                type yang:date-and-time;
                config false;
                description "Date and time when the content of the current
                    version of this vendor configuration file was first applied by the
                    CPE.";
            }

            leaf Descritpion {
                type string {
                    length "0..256";
                }
                config false;
                description "A description of the vendor configuration file
                    (human-readable string).";
            }

        } // list VendorConfigFile
    } // grouping VendorConfigFile
} // module
