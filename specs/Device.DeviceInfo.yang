module Device.DeviceInfo {

    yang-version 1;

    namespace "urn:telekom:tr181:device:2:deviceinfo";

    prefix "Device.DeviceInfo";

    import ietf-yang-types { prefix yang; }
    include Device.DeviceInfo.VendorConfigFile;
    include Device.DeviceInfo.SupportedDataModel;
    include Device.DeviceInfo.NetworkProperties;

    organization "Deutsche Telekom AG";

    contact 
        'Web:   <http://opencpe.org/contact>
Email: OpenCPE Support
       <mailto:support@opencpe.org>';

    description
        'Copyright (c) 2013 Deutsche Telekom AG

This module is the DeviceInfo branch of the Device:2 Datamodel for TR-069/WT-181.
';

    revision "2013-09-22" {
        description "Version 0.1.0 -- Initial release";
    }

    grouping DeviceInfo {
        description "This object contains general device information.";

        leaf Manufacturer {
            type string {
                length "0..64";
            }
            default "Travelping GmbH";
            config false;
            description
                "The manufacturer of the CPE (human readable string).";
        }

        leaf ManufacturerOUI {
            type string {
                length 6;
                pattern "[A-F0-9]{6}";
            }
            default "001F30";
            config false;
            description
                "Organizationally unique identifier of the device
                manufacturer.  Represented as a six hexadecimal-digit value using all
                upper-case letters and including any leading zeros.  The value MUST be a
                valid OUI as defined in http://standards.ieee.org/faqs/OUI.html.
                This value MUST remain fixed over the lifetime of the device, including
                across firmware updates. Any change would indicate that it's a new
                device and would therefore require a BOOTSTRAP Inform.";
            reference "http://standards.ieee.org/faqs/OUI.html";
        }

        leaf ModelName {
            type string {
                length "0..64";
            }
            config false;
            description
                "Model name of the CPE (human readable string).";
        }

        leaf Description {
            type string {
                length "0..256";
            }
            config false;
            description
                "A full description of the CPE device (human readable
                string).";
        }

        leaf ProductClass {
            type string {
                length "0..64";
            }
            config false;
            description
                "Identifier of the class of product for which the serial
                number applies. That is, for a given manufacturer, this parameter is
                used to identify the product or class of product over which the
                SerialNumber  parameter is unique.
                This value MUST remain fixed over the lifetime of the device, including
                across firmware updates. Any change would indicate that it's a new
                device and would therefore require a BOOTSTRAP Inform.";
        }

        leaf SerialNumber {
            type string {
                length "0..64";
            }
            config false;
            description
                "Identifier of the particular device that is unique for the
                indicated class of product and manufacturer.
                This value MUST remain fixed over the lifetime of the device, including
                across firmware updates. Any change would indicate that it's a new device
                and would therefore require a BOOTSTRAP Inform.";
        }

        leaf HardwareVersion {
            type string {
                length "0..64";
            }
            config false;
            description
                "A string identifying the particular CPE model and version.";
        }

        leaf SoftwareVersion{
            type string {
                length "0..64";
            }
            config false;
            description
                "A string identifying the software version currently
                installed in the CPE (i.e. version of the overall CPE firmware).
                To allow version comparisons, this element SHOULD be in the form of dot-
                delimited integers, where each successive integer represents a more minor
                category of variation. For example, 3.0.21 where the components mean:
                Major.Minor.Build.";
        }

        leaf-list EnabledOptions {
            type string;
            config false;
            description
                "List of strings. Each entry is the OptionName of each
                Option that is currently enabled in the CPE. The OptionName of each is
                identical to the OptionName element of the OptionStruct described in
                [TR-069a2]. Only those options are listed whose State indicates the
                option is enabled.";
        }

        leaf-list AdditionalHardwareVersion {
            type string {
                length "0..64";
            }
            config false;
            description
                "Each entry is an additional version. Represents any
                additional hardware version information the vendor might wish to
                supply.";
        }

        leaf-list AdditionalSoftwareVersion {
            type string {
                length "0..64";
            }
            config false;
            description
                "Each entry is an additional version. Represents any
                additional software version information the vendor might wish to
                supply.";
        }

        leaf ProvisioningCode {
            type string {
                length "0..64";
            }
            config true;
            description
                "Identifier of the primary service provider and other
                provisioning information, which MAY be used by the ACS to determine
                service provider-specific customization and provisioning parameters.";
        }

        leaf DeviceStatus {
            /*
               WT-181i2 defines this as of type string but since it can
               only take some defined values the programmers agreed, that
               it is better implemented as an enumeration.
             */
            type enumeration {
                enum Up;
                enum Initializing;
                enum Error; enum Disabled;
            }
            config false;
            description
                "Current operational status of the device. Enumeration of:
                * Up
                * Initializing
                * Error
                * Disabled";
        }

        leaf UpTime {
            type uint32;
            config false;
            description
                "Time in seconds since the CPE was last restartet.";
        }

        leaf FirstUseDate {
            type yang:date-and-time;
            config false;
            description
                "Date and Time in UTC that the CPE first both successfully
                established an IP-layer network connection and acquired an absolute time
                reference using NTP or equivalent over that network connection. The CPE
                MAY reset this date after a factory reset.
                If NTP or equivalent is not available, this parameter, if
                present, SHOULD be set to the Unknown Time Value.";
        }

        leaf VendorConfigFileNumberOfEntries {
            type uint32;
            config false;
            default 0;
            description
                "The number of entries in the VendorConfigFile table.";
        }

        leaf SupportedDataModelNumberOfEntries {
            type uint32;
            config false;
            default 0;
            description
                "Number of entries in the SupportedDataModel table.";
        }

        // import Device.DeviceInfo.VendorConfigFile
        //      uses DevInfVend:VendorConfigFile;

        // import Device.DeviceInfo.SupportedDataModel
        //      uses DevInfSup:SupportedDataModel;


        // import Device.DeviceInfo.NetworkProperties
        //      uses DevInfNet:NetworkProperties;

    } // grouping DeviceInfo
} // module DeviceInfo
