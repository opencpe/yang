submodule Device.RPC.CPE {

    yang-version 1;

    belongs-to Device.RPC {prefix Device.RPC;}

    import ietf-inet-types {prefix inet;}
    import ietf-yang-types {prefix yang;}

    organization "Deutsche Telekom AG";

    contact 
        'Web:   <http://opencpe.org/contact>
Email: OpenCPE Support
       <mailto:support@opencpe.org>';

    description
        'Copyright (c) 2013 Deutsche Telekom AG

This submodule models CPE RPC methods for the TR-069 Amandment 2 data model. Only an ACS can call these methods.
';

    revision "2013-09-22" {
        description "Version 0.1.0 -- Initial release";
    }

    // *****************************************************************
    // baseline CPE RPC Methods
    // *****************************************************************

    rpc SetParameterValues {
        description "This method MAY be used by an ACS to modify the value
            of one or more CPE Parameters.

            On successful receipt of a SetParameterValues RPC, the CPE MUST apply
            the changes to all of the specified Parameters atomically. That is,
                either all of the value changes are applied together, or none of the
                    changes are applied at all. In the latter case, the CPE MUST return a
                    fault response indicating the reason for the failure to apply the
                    changes. The CPE MUST NOT apply any of the specified changes without
                    applying all of them. This requirement MUST hold even if the CPE
                    experiences a crash during the process of applying the changes. The
                    order of Parameters listed in the ParameterList has no significance:
                    the application of value changes to the CPE MUST be independent from
                    the order in which they are listed.
                    If the request is valid, it is strongly RECOMMENDED that the CPE apply
                    the requested changes prior to sending the SetParameterValues response.
                    If it does so, the CPE MUST set the value of Status in the response to
                    0 (zero), indicating that the changes have been applied.
                    If the CPE requires the session to be terminated before applying some
                    or all of the Parameter values, the CPE MUST reply before all
                    Parameter values have been applied, and thus MUST set the value of
                    Status in the response to 1. In this case, the reply MUST come only
                    after all validation of the request has been completed and the new
                    values have been appropriately saved such that they will definitely be
                    applied as soon as physically possible after the session has
                    terminated. Once the CPE issues the SetParameterValues response, all
                    changes associated with the corresponding request (including the new
                            ParameterKey) MUST be available for subsequent commands to operate on,
                regardless of whether the changes have been applied or not. In
                    particular, the use of GetParameterValues to read a parameter modified
                    by an earlier SetParameterValues MUST return the modified value, even
                    if that value has not yet been applied.
                        If the value of Status in the SetParameterValues response is 1, the
                            requested changes MUST be applied as soon as physically possible after
                            the session has terminated, and no later than the beginning of the
                            next session. Note that if a CPE requires a reboot to cause the
                            changes to be applied, the CPE MUST initiate that reboot on its own
                            after the termination of the session. Because some CPE will not
                            require a reboot in these circumstances, an ACS SHOULD NOT call the
                            Reboot method as a result of modifying the CPE's configuration, since
                            this would result in an unnecessary reboot. Note also that if
                            application of a configuration change by the CPE would result in a
                            service disruption (for example, if the CPE requires a reboot to apply
                                    the requested change), it is not the responsibility of the CPE to
                            avoid or delay such a disruption. To minimize the impact of such a
                            disruption, the ACS MAY delay requesting such a configuration change
                            until an appropriate time, but this is entirely at the ACS's
                            discretion.
                            The use of the Status value is independent between successive
                            SetParameterValues, AddObject, or DeleteObject requests within the
                            same session. The use of a Status value of 1 in response to one
                            request does not necessarily imply that subsequent requests in the
                            same session will also respond in the same way.
                            The ACS MAY set parameter values in any combination or order of its
                            choosing using one or multiple SetParameterValues RPCs.
                            All modifications to a CPE's configuration resulting from use of the
                            SetParameterValues method MUST be retained across reboots of the CPE.
                            The following fault codes are defined for this method: 9001, 9002,
                                9003, 9004, 9005, 9006, 9007, 9008.
                                    If there is a fault due to one or more parameters in error, the fault
                                    response for this method MUST include a SetParameterValuesFault
                                    element for each parameter in error. In this case, the primary fault
                                    code indicated for the overall fault response MUST be Invalid
                                    Arguments (9003).
                                    The CPE MUST reject an attempt to set values using the
                                    SetParameterValues RPC that would result in an invalid configuration,
                                where an invalid configuration is defined as one of the following:
                                    1) A parameter value or combination of parameter values that are
                                    explicitly prohibited in the definition of the data model(s)
                                    supported by the CPE.
                                    2) A parameter value or combination of parameter values that are not
                                    supported by the CPE and are not required by the data model(s) or
                                    profiles (as defined in [13]) supported by the CPE.
                                    In both of the above cases, the response from the CPE MUST include a
                                    SetParameterValuesFault element for each such parameter, indicating
                                    the Invalid Parameter Value fault code (9007).
                                    The CPE MUST NOT impose any additional configuration restrictions
                                    beyond the exceptions described above and restrictions otherwise
                                    explicitly permitted or required by the CPE WAN Management Protocol.";

        input {

            list ParameterList {
                description "Array of name-value pairs as specified in
                    ParameterValueStruct. For each name-value pair, the CPE is instructed
                    to set the Parameter specified by the name to the corresponding value.
                    This array MUST NOT contain more than one entry with the same
                    Parameter name. If a given Parameter appears in this array more than
                    once, the CPE MUST respond with fault 9003 (Invalid arguments).
                    If the length of this array is zero, then the CPE MUST set the
                    ParameterKey to the value specified by the ParameterKey argument,
                                 but MUST NOT set any other parameter values.";
                key Name;
                leaf Name {
                    type string {
                        length 256;
                    }
                    description "This is the name of a Parameter. The CPE MUST
                        treat the parameter name as case sensitive.";
                }

                anyxml Value {
                    description "This is the value the Parameter is to be set.";
                }
            } // list Parameterlist

            leaf ParameterKey {
                type string {
                    length 32;
                }
                description "The value to set the ParameterKey parameter.
                    The CPE MUST set ParameterKey to the value specified in this argument
                    if and only if SetParameterValues completes successfully and no fault
                        response is generated. If SetParameterValues does not complete
                            successfully (implying that the parameter value changes requested did
                                    not take effect), the value of ParameterKey MUST NOT be modified.
                            ParameterKey provides the ACS a reliable and extensible means to
                            track changes made by the ACS. The value of this argument is left to
                            the discretion of the ACS, and MAY be left empty.";
            }
        }

        output {
            leaf Status {
                type int32 {
                    range "0..1";
                }
                description "A successful response to this method returns
                    an integer enumeration defined as follows:
                    0 = All Parameter changes have been validated and applied.
                    1 = All Parameter changes have been validated and committed, but some
                    or all are not yet applied (for example, if a reboot is required before
                            the new values are applied).";
            }
        }
    }

    // ***************************************************************

    rpc GetParameterValues {
        description "This method MAY be used by an ACS to obtain the
            value of one or more CPE Parameters.
            The following fault codes are defined for this method: 9001, 9002,
                9003, 9004, 9005.
                    If the fault is caused by one or more invalid parameter names in the
                    ParameterNames array, the Invalid Parameter Name fault code (9005) MUST
                    be used instead of the more general Invalid Arguments fault code
                    (9003). The value of a ParameterNames element MUST be considered
                    invalid if it does not exactly match either the name of a parameter
                    currently present in the CPE's data model (if the ParameterNames
                            element does not end with a dot) or the name of an object currently
                    present in the CPE's data model (if ParameterNames element ends with a
                            dot).";

        input {
            leaf-list ParameterNames {
                type string {
                    length 256;
                }
                description "Array of strings, each representing the name
                    of a requested Parameter. If a Parameter name argument is given as a
                    partial path name, the request is to be interpreted as a request to
                    return all of the Parameters in the branch of the naming hierarchy that
                    shares the same prefix as the argument. A partial path name MUST end
                    with a '.' (dot) after the last node name in the hierarchy. An empty
                    string indicates the top of the name hierarchy.
                    Below is an example of a full Parameter name:
                    InternetGatewayDevice.DeviceInfo.SerialNumber
                    Below is an example of a partial path name:
                    InternetGatewayDevice.DeviceInfo.";
            }
        }

        output {

            list ParameterList {
                description "Array of name-value pairs, as specified in
                    ParameterValueStruct, containing the name and value for each requested
                    Parameter.
                    If multiple entries in the ParameterNames array in the
                    GetParameterValues request overlap such that there are multiple
                    requests for the same Parameter value, it is at the discretion of the
                    CPE whether or not to duplicate that Parameter in the response array.
                    That is, the CPE MAY either include that Parameter value only once in
                    its response, or it MAY include that Parameter value once for each
                    instance that it was requested.";
                key Name;
                leaf Name {
                    type string {
                        length 256;
                    }
                    description "This is the name of a Parameter. The CPE MUST
                        treat the parameter name as case sensitive.";
                }

                anyxml Value {
                    description "This is the value the Parameter is to be set.";
                }
            }

        }
    }

    // ***************************************************************

    rpc GetParameterNames {
        description "This method may be used by a ACS to discover the
            Parameters accessible on a particular CPE.
            The following fault codes are defined for this method: 9001, 9002,
                9003, 9005.
                    If the fault is caused by an invalid ParameterPath value, the Invalid
                    Parameter Name fault code (9005) MUST be used instead of the more
                    general Invalid Arguments fault code (9003). A ParameterPath value MUST
                    be considered invalid if it is not an empty string and does not exactly
                    match a parameter or object name currently present in the CPE's data
                    model. If NextLevel is true and ParameterPath is a Parameter name
                    rather than a partial path, the CPE MUST return a fault response with
                    the Invalid Arguments fault code (9003).";

        input {
            leaf ParameterPath {
                type string {
                    length 256;
                }
                description "A string containing either a complete
                    Parameter name, or a partial path name representing a subset of the
                    name hierarchy. An empty string indicates the top of the name hierarchy.
                    A partial path name MUST end with a '.' (dot) after the last node name
                    in the hierarchy.
                    Below is an example of a full Parameter name:
                    InternetGatewayDevice.DeviceInfo.SerialNumber
                    Below is an example of a partial path name:
                    InternetGatewayDevice.DeviceInfo.";
            }

            leaf NextLevel {
                type boolean;
                description "If false, the response MUST contain the
                    Parameter or object whose name exactly matches the ParameterPath
                    argument, plus all Parameters and objects that are descendents of the
                    object given by the ParameterPath argument, if any (all levels below
                            the specified object in the object hierarchy). For example, if
                    ParameterPath were 'InternetGatewayDevice.LANDevice.1.Hosts.', the
                    response would include the following (if there were a single instance
                            of Host with instance number '1'):
                        InternetGatewayDevice.LANDevice.1.Hosts.
                        InternetGatewayDevice.LANDevice.1.Hosts.HostNumberOfEntries
                        InternetGatewayDevice.LANDevice.1.Hosts.Host.
                        InternetGatewayDevice.LANDevice.1.Hosts.Host.1.
                        InternetGatewayDevice.LANDevice.1.Hosts.Host.1.IPAddress
                        InternetGatewayDevice.LANDevice.1.Hosts.Host.1.AddressSource
                        InternetGatewayDevice.LANDevice.1.Hosts.Host.1.LeaseTimeRemaining
                        InternetGatewayDevice.LANDevice.1.Hosts.Host.1.MACAddress
                        InternetGatewayDevice.LANDevice.1.Hosts.Host.1.HostName
                        InternetGatewayDevice.LANDevice.1.Hosts.Host.1.InterfaceType
                        InternetGatewayDevice.LANDevice.1.Hosts.Host.1.Active
                        If true, the response MUST contain all Parameters and objects that are
                        next-level children of the object given by the ParameterPath argument,
                        if any. For example, if ParameterPath were
                        'InternetGatewayDevice.LANDevice.1.Hosts.', the response would include
                        the following:
                        InternetGatewayDevice.LANDevice.1.Hosts.HostNumberOfEntries
                        InternetGatewayDevice.LANDevice.1.Hosts.Host.
                        Or, if ParameterPath were empty, with NextLevel equal true, the
                        response would list only 'InternetGatewayDevice.' (if the CPE is an
                                Internet Gateway Device).";
            }
        }

        output {

            list ParameterList {
                description "Array of structures, each containing the
                    name and other information for a Parameter or object, as defined in
                    ParameterInfoStruct.
                    When NextLevel is false, this list MUST contain the Parameter or object
                    whose name exactly matches the ParameterPath argument, plus all
                    Parameters and objects that are descendents of the object given by the
                    ParameterPath argument, if any (all levels below the specified object in
                            the object hierarchy). If the ParameterPath argument is an empty
                    string, names of all objects and Parameters accessible on the particular
                    CPE are returned.
                    When NextLevel is true, this list MUST contain all Parameters and object
                    that are next-level children of the object given by the ParameterPath
                    argument, if any.
                    For a Parameter, the Name returned in this structure MUST be a full path
                    name, ending with the name of the Parameter element. For an object, the
                    Name returned in this structure MUST be a partial path, ending with a
                    dot.
                    This list MUST include any objects that are currently empty. An empty
                    object is one that contains no instances (for a multi-instance object),
                           no child objects, and no child Parameters.
                               If NextLevel is true and ParameterPath refers to an object that is
                               empty, this array MUST contain zero entries.
                               The ParameterList MUST include only Parameters and objects that are
                               actually implemented by the CPE. If a Parameter is listed, this implies
                               that a GetParameterValues for this Parameter would be expected to
                               succeed.";
                key Name;
                leaf Name {
                    type string {
                        length 256;
                    }
                    description "This is the name of a Parameter or partial path
                        name.";
                }

                leaf Writable {
                    type boolean;
                    description "Whether or not the Parameter value can be
                        overwritten using the SetParameterValues method.
                        If Name is a partial path that refers to an object, this indicates
                        whether or not AddObject can be used to add new instances of this
                        object.
                        If Name is a partial path that refers to a particular instance of a
                        multi-instance object, this indicates whether or not DeleteObject can
                        be used to remove this particular instance.
                        This element MUST be true only if the corresponding Parameter or object
                        as implemented in this CPE is writable as described above. The value of
                        this element MUST reflect only the actual implementation rather than
                        whether or not the specification of the Parameter or object allows it
                        to be writable.";
                }
            }
        }
    }

    // ***************************************************************

    rpc SetParameterAttributes {
        description "This method MAY be used by an ACS to modify
            attributes associated with one or more CPE Parameter.
            On successful receipt of a SetParameterAttributes RPC, the CPE MUST
            apply the changes to all of the specified Parameters immediately and
            atomically. That is, either all of the attribute changes are applied
            together, or none of the changes are applied at all. In the latter
            case, the CPE MUST return a fault response indicating the reason for
            the failure to apply the changes. The CPE MUST NOT apply any of the
            specified changes without applying all of them. This requirement MUST
            hold even if the CPE experiences a crash during the process of applying
            the changes.
            The ACS MAY set parameter attributes in any combination or order of its
            choosing using one or multiple SetParameterAttributes RPCs.
            If there is more than one entry in the ParameterList array, and the
            SetParameterAttributes request is successful as described above, the
            CPE MUST apply the attribute changes in the order of the ParameterList
            array. That is, if multiple entries in the ParameterList would result
            in modifying the same attribute of a given parameter, the attribute
            value specified later in the ParameterList array MUST overwrite the
            attribute value specified earlier in the array. This behavior might
            seem to be inconsistent with that of SetParameterValues, for which it
            is an error to specify the same parameter name more than once; this
            difference is because, unlike SetParameterValues,
                       SetParameterAttributes permits a mixture of full and partial paths to
                           be specified.
                           All modifications to a CPE's configuration resulting from use of the
                           SetParameterAttributes method MUST be retained across reboots of the
                           CPE.
                           A CPE MUST NOT allow any entity other than the ACS to modify attributes
                           of a parameter.
                           The following fault codes are defined for this method: 9001, 9002,
                       9003, 9004, 9005, 9009.
                           If the fault is caused by an invalid parameter name, the Invalid
                           Parameter Name fault code (9005) MUST be used instead of the more
                           general Invalid Arguments fault code (9003). If the CPE does not support
                           Active Notifications on a parameter deemed inappropriate (as described
                                   above), it MUST reject an attempt to enable Active Notification for
                           that parameter by responding with fault 9009 (Notification request
                                   rejected). If Active notification is being enabled for parameter(s)
                           specified via a partial path and the CPE does not support Active
                           notification for one or more such parameters deemed inappropriate below
                           this point in the naming hierarchy, the CPE MUST reject the request and
                           respond with fault code 9009 (Notification request rejected).";


        input {

            list ParameterList {
                description "List of changes to be made to the attributes
                    for a set of Parameters. Each entry in this array is a SetParameter-
                        AttributesStruct as defined in SetParameterAttributesStruct.
                            As described above, the order of entries in this array is significant.";
                key Name;
                leaf Name {
                    type string {
                        length 256;
                    }
                    description "This is the name of a Parameter to apply the new
                        attributes. Alternatively, this MAY be a partial path name, indicating
                        that the new attributes are to be applied to all Parameters below this
                        point in the naming hierarchy. For such Parameters within multi-
                        instance objects where the instance number is below the specified point
                        in the naming hierarchy, the specified attribute values MUST only be
                        applied within instances that exist at the time this method is invoked.
                        A partial path name MUST end with a '.' (dot) after the last node name
                        in the hierarchy. An empty string indicates the top of the name
                        hierarchy.
                        Below is an example of a full Parameter name:
                        InternetGatewayDevice.DeviceInfo.SerialNumber
                        Below is an example of a partial path name:
                        InternetGatewayDevice.DeviceInfo.";
                }

                leaf NotificationChange {
                    type boolean;
                    description "If true, the value of Notification replaces the
                        current notification setting for this parameter or group of parameters.
                        If false, no change is made to the notification setting.";
                }

                leaf Notification {
                    type int32 {
                        range "0..2";
                    }
                    description "Indicates whether the CPE will include changed
                        values of the specified parameter(s) in the Inform message, and whether
                        the CPE will initiate a session to the ACS when the specified
                        parameter(s) change in value. The following values are defined:
                        0 = Notification off. The CPE need not inform the ACS of a change to
                        the specified parameter(s).
                        1 = Passive notification. Whenever the specified parameter value
                        changes, the CPE MUST include the new value in the ParameterList in the
                        Inform message that is sent the next time a session is established to
                        the ACS. If the CPE has rebooted, or the URL of the ACS has changed
                        since the last session, the CPE MAY choose not to include the list of
                        changed parameters in the first session established with the new ACS.
                        2 = Active notification. Whenever the specified parameter value
                        changes, the CPE MUST initiate a session to the ACS, and include the
                        new value in the ParameterList in the associated Inform message. For
                        parameters defined in the corresponding data model as requiring Forced
                        Active Notification, the value of the Notification attribute is
                        irrelevant and an attempt to set it to a value other than 2 will be
                        ignored. Whenever a parameter change is sent in the Inform message due
                        to a non-zero Notification setting, the Event code '4 VALUE CHANGE'
                        MUST be included in the list of Events. Note that if the CPE deletes
                        an object containing parameters for which Notification is enabled
                        (active or passive), this MUST NOT be considered a value-change for
                        the purpose of Notification. By default, prior to any changes to this
                        attribute by an ACS, its value SHOULD be 0 (Notification off) unless
                        otherwise specified in the appropriate data model definition. The CPE
                        MAY provide no support for Active Notification on a parameter deemed
                        inappropriate for Active Notification. A parameter is deemed
                        inappropriate for Active Notification if and only if that parameter is
                        explicitly defined as such in the definition of the corresponding data
                        model. Parameters that might be deemed inappropriate for Active
                        Notification include parameters that change frequently, such as
                        statistics. A CPE MUST accept a request to enable Passive Notification
                        for any parameter. Note that if a CPE implementation does not allow a
                            particular parameter value to change in a manner that would result in a
                                Notification (e.g., a capability flag that could only change as a
                                        result of a firmware update that requires a reboot, or a writeable
                                        parameter that can only be modified via the CPE WAN Management
                                        Protocol), then support for Notification for this parameter involves no
                                more than keeping track of the value of its Notification attribute.
                                For such a parameter, the CPE implementation need not incorporate a
                                mechanism to detect value changes nor to initiate Notifications based
                                on such changes.";
                }

                leaf AccessListChange {
                    type boolean;
                    description "If true, the value of AccessList replaces the
                        current access list for this parameter or group of parameters.
                        If false, no change is made to the access list.";
                }

                leaf-list AccessList {
                    type string {
                        length 64;
                    }
                    description "Array of zero or more entities for which write
                        access to the specified Parameter(s) is granted. If there are no
                        entries, write access is only allowed from an ACS.
                        At present, only one type of entity is defined that can be included in
                        this list: 'Subscriber' Indicates write access by an interface
                        controlled on the subscriber LAN. Includes any and all such LAN-side
                        mechanisms, which MAY include but are not limited to TR-064 (LAN-side
                                DSL CPE Configuration Protocol), UPnP, the device's user interface,
                        client-side telnet, and client-side SNMP.
                            Currently, access restrictions for other WAN-side configuration
                            protocols is not specified. The ACS MAY further specify management
                            entities in the ACL using a vendor-specific prefix. If such entities
                            are specified by vendors, they MUST be preceded by X_<VENDOR>_and
                            follow the syntax for vendor extensions for parameter names defined in
                            TR-106 Amendment 1, Data Model Template for TR-069-Enabled Devices,
                        Broadband Forum Technical Report.
                            The CPE MUST correctly interpret the value 'Subscriber' as described
                            above, but MUST ignore any other individual values in this array that
                            it does not understand.
                            By default, prior to any changes to the access list by an ACS, access
                            SHOULD be granted to all entities specified above.
                            The TR-069 ACS always has write access to all writeable parameters
                            regardless of being on the access list. Other entities have write
                            access only if they appear on the access list. An entity that is
                            restricted from write access to a certain parameter MUST NOT be allowed
                            to change parameter values and MUST NOT be allowed to delete objects
                            within which the parameter is contained. The TR-069 access control
                            mechanism does not prevent any entity from creating new object
                            instances.
                            The CPE MUST accept changes to the AccessList for any Parameter even if
                            that Parameter is read-only and its value cannot be modified by any
                            management entity. For such read-only Parameters, the CPE MUST store
                            the modified AccessList value and return it when requested via
                            GetParameterAttributes, but MAY otherwise ignore this value.";
                }
            }
        }
        // optional and empty, therefore omitted
        //          output {}
    }

    // ***************************************************************

    rpc GetParameterAttributes {
        description "This method MAY be used by an ACS to read the
            attributes associated with one or more CPE Parameter.
            The following fault codes are defined for this method: 9001, 9002,
                9003, 9004, 9005.
                    If the fault is caused by an invalid parameter name, the Invalid
                    Parameter Name fault code (9005) MUST be used instead of the more
                    general Invalid Arguments fault code (9003).";

        input {
            leaf-list ParameterNames {
                type string {
                    length 256;
                }
                description "Array of strings, each representing the name
                    of a requested Parameter.
                    If a Parameter name argument is given as a partial path name, the
                    request is to be interpreted as a request to return all of the
                    Parameters in the branch of the naming hierarchy that shares the same
                    prefix as the argument. A partial path name MUST end with a '.' (dot)
                    after the last node name in the hierarchy. An empty string indicates
                    the top of the name hierarchy.
                    Below is an example of a full Parameter name:
                    InternetGatewayDevice.DeviceInfo.SerialNumber
                    Below is an example of a partial path name:
                    InternetGatewayDevice.DeviceInfo.";
            }
        }

        output {

            list ParameterList {
                description "List of access control information for the
                    specified set of Parameters. Each entry in this array is a
                    ParameterAttributeStruct as defined in ParameterAttributesStruct.
                    If the ParameterNames argument in the request was a partial path,
                       and if there are no Parameters within the object represented by that
                           partial path (at any level below), the ParameterList MUST be empty,
                       and this MUST NOT cause an error response.";
                key Name;
                leaf Name {
                    type string {
                        length 256;
                    }
                    description "This is the name of a Parameter to which the
                        attributes are given.The Name MUST be a full Parameter name, and MUST
                        NOT be a partial path.";
                }

                leaf Notification {
                    type int32 {
                        range "0..2";
                    }
                    description "Indicates whether the CPE will include changed
                        values of the specified parameter(s) in the Inform message, and whether
                        the CPE will initiate a session to the ACS when the specified
                        parameter(s) change in value. The following values are defined:
                        0 = Notification off. The CPE need not inform the ACS of a change to
                        the specified parameter(s).
                        1 = Passive notification. Whenever the specified parameter value
                        changes, the CPE MUST include the new value in the ParameterList in the
                        Inform message that is sent the next time a session is established to
                        the ACS.
                        2 = Active notification. Whenever the specified parameter value
                        changes, the CPE MUST initiate a session to the ACS, and include the
                        new value in the ParameterList in the associated Inform message.";
                }

                leaf-list  AccessList {
                    type string {
                        length 64;
                    }
                    description "Array of zero or more entities for which write
                        access to the specified Parameter(s) is granted. If there are no
                        entries, write access is only allowed from an ACS. At present, only one
                        type of entity is defined that can be included in this list:
                        'Subscriber' Indicates write access by an interface controlled on the
                        subscriber LAN. Includes any and all such LAN-side mechanisms, which MAY
                        include but are not limited to TR-064 (LAN-side DSL CPE Configuration
                                Protocol), UPnP, the device's user interface, client-side telnet, and
                        client-side SNMP.
                        The list MAY include vendor-specific entities, which MUST be preceded
                        by X_<VENDOR>_and follow the syntax for vendor extensions for parameter
                        names defined in TR-106 Amendment 1, Data Model Template for TR-069-
                        Enabled Devices, Broadband Forum Technical Report.
                        The ACS MAY ignore any individual items in this array that it does not
                        understand.
                        By default, prior to any changes to the access list by an ACS, the
                        AccessList attribute for all parameters SHOULD include all entities
                        that the CPE supports, indicating access granted to all of these
                        entities.";
                }
            }
        }
    }

    // ***************************************************************

    rpc AddObject {
        description "This method MAY be used by the ACS to create a new
            instance of a multi-instance object-a collection of Parameters and/or
            other objects for which multiple instances are defined. The method call
            takes as an argument the path name of the collection of objects for
            which a new instance is to be created. For example:
            Top.Group.Object.
            This path name does not include an instance number for the object to be
            created. That instance number is assigned by the CPE and returned in
            the response. Once assigned the instance number of an object cannot be
            changed and persists until the object is deleted using the DeleteObject
            method. After creation, Parameters or sub-objects within the object are
            referenced by the path name appended with the instance number. For
            example, if the AddObject method returned an instance number of 2, a
            Parameter within this instance can then be referred to by the path:
            Top.Group.Object.2.Parameter
            On creation of an object using this method, the Parameters contained
            within the object MUST be set to their default values and the
            associated attributes MUST be set to the following:
            - Notification is set to zero (notification off) unless otherwise
            specified in the appropriate data model definition
            - AccessList includes all defined entities
            Addition of an object MUST be done atomically. That is, either all of
            the Parameters and sub-objects are added together, or none are added.
            In the latter case the CPE MUST return a fault response indicating the
            reason for the failure to add the object. The CPE MUST NOT add any
            contained Parameters or sub-objects as a result of this method call
            without adding all of them (all Parameters and sub-objects supported by
                    that CPE). This requirement MUST hold even if the CPE experiences a
            crash during the process of performing the addition.
            If the request is valid, it is strongly RECOMMENDED that the CPE apply
            the object creation prior to sending the AddObject response. If it does
            so, the CPE MUST set the value of Status in the response to 0 (zero),
            indicating that the object creation has been applied.
                If the CPE requires the session to be terminated before applying the
                object creation, the CPE MUST reply before the object creation has been
                applied, and thus MUST set the value of Status in the response to 1. In
                this case, the reply MUST come only after all validation of the request
                has been completed and the object creation request has been
                appropriately saved such that it will definitely be applied as soon as
                physically possible after the session has terminated. Once the CPE
                issues the AddObject response, all changes associated with the
                corresponding request (including the new ParameterKey) MUST be
                available for subsequent commands to operate on, regardless of whether
                the changes have been applied or not. In particular, even if the object
                creation has not yet been applied, the CPE MUST allow the use of
                SetParameterValues, GetParameterValues, SetParameterAttributes, and
                GetParameterAttributes to operate on parameters within the newly
                created object, as well as the use of AddObject to create a sub-object
                within the newly created object, and DeleteObject to delete either a
                sub-object or the newly created object itself.
                If the value of Status in the AddObject response is 1, the requested
                object creation MUST be applied as soon as physically possible after
                the session has terminated, and no later than the beginning of the next
                session. Note that if a CPE requires a reboot to cause the object
                creation to be applied, the CPE MUST initiate that reboot on its own
                after the termination of the session. Because some CPE will not require
                a reboot in these circumstances, an ACS SHOULD NOT call the Reboot
                method as a result of modifying the CPE's configuration, since this
                would result in an unnecessary reboot. Note also that if application of
                a configuration change by the CPE would result in a service disruption
                (for example, if the CPE requires a reboot to apply the requested
                 change), it is not the responsibility of the CPE to avoid or delay such
                a disruption. To minimize the impact of such a disruption, the ACS MAY
                delay requesting such a configuration change until an appropriate time,
            but this is entirely at the ACS's discretion.
                The use of the Status value is independent between successive
                SetParameterValues, AddObject, or DeleteObject requests within the same
                session. The use of a Status value of 1 in response to one request does
                not necessarily imply that subsequent requests in the same session will
                also respond in the same way.
                All modifications to a CPE's configuration resulting from use of the
                AddObject method MUST be retained across reboots of the CPE. This MUST
                include the values of object instance numbers.
                The following fault codes are defined for this method: 9001, 9002,
            9003, 9004, 9005.
                If an AddObject request would result in exceeding the maximum number of
                such objects supported by the CPE, the CPE MUST return a fault response
                with the Resources Exceeded (9004) fault code.";

        reference "TR-069 Appendix B";

        input {
            leaf ObjectName {
                type string {
                    length 256;
                }
                description "The path name of the collection of objects for
                    which a new instance is to be created.
                    The path name MUST end with a '.' (dot) after the last node in the
                    hierarchical name of the object.";
            }

            leaf ParameterKey {
                type string {
                    length 32;
                }
                description "The value to set the ParameterKey parameter.
                    The CPE MUST set ParameterKey to the value specified in this argument
                    if and only if AddObject completes successfully and no fault response
                        is generated. If AddObject does not complete successfully (implying
                                that the requested object did not get added), the value of ParameterKey
                            MUST NOT be modified. ParameterKey provides the ACS a reliable and
                            extensible means to track changes made by the ACS. The value of this
                            argument is left to the discretion of the ACS, and MAY be left empty.";
            }
        }

        output {
            leaf InstanceNumber {
                type uint32 {
                    range "1..max";
                }
                description "The instance number of the newly created
                    object. Once created, a Parameter or sub-object within this object can
                    be later referenced by using this instance number in the path name. The
                    instance number assigned by the CPE is arbitrary and instance numbers
                    assigned by sequential calls to AddObject need not be consecutive.
                    The CPE SHOULD NOT assign an instance number that has been used for a
                    previously deleted object instance. The CPE SHOULD exhaust the full
                    space of integer values for a given object before re-using instance
                    numbers.
                    Once an object instance is created, the assigned instance number MUST
                    persist unchanged until the object is subsequently deleted (either by
                            the ACS or by a third party). This implies that the instance number
                    MUST persist across reboots of the CPE, and that the CPE MUST NOT allow
                    the instance number of an existing object instance to be modified by a
                    third-party entity.";
            }

            leaf Status {
                type int32 {
                    range "0..1";
                }
                description "A successful response to this method returns
                    an integer enumeration defined as follows:
                    0 = The object has been created.
                    1 = The object creation has been validated and committed, but not yet
                    applied (for example, if a reboot is required before the new object can
                            be applied).";
            }
        }
    }

    // ***************************************************************

    rpc DeleteObject {
        description "This method is used to remove a particular
            instance of an object. This method call takes as an argument the path
            name of the object instance including the instance number. For example:
            Top.Group.Object.2.
            If this method call is successful, the specified instance of this
            object is subsequently unavailable for access and the CPE MUST discard
            the state previously associated with all Parameters (values and
                    attributes) and sub-objects contained within this instance.
            When an object instance is deleted, the instance numbers associated
            with any other instances of the same collection of objects remain
            unchanged. Thus, the instance numbers of object instances in a
            collection might not be consecutive.
            If the request is valid, it is strongly RECOMMENDED that the CPE apply
            the object deletion prior to sending the DeleteObject response. If it
            does so, the CPE MUST set the value of Status in the response to 0
            (zero), indicating that the object deletion has been applied.
            If the CPE requires the session to be terminated before applying the
            object deletion, the CPE MUST reply before the object deletion has been
            applied, and thus MUST set the value of Status in the response to 1. In
            this case, the reply MUST come only after all validation of the request
            has been completed and the object deletion request has been
            appropriately saved such that it will definitely be applied as soon as
            physically possible after the session has terminated. Once the CPE
            issues the DeleteObject response, all changes associated with the
            corresponding request (including the new ParameterKey) MUST be
            available for subsequent commands to operate on, regardless of whether
            the changes have been applied or not. In particular, the use of
            GetParameterNames and GetParameterValues MUST indicate the absence of
            the deleted object, and any attempt to modify or read parameters or sub-
            objects within the deleted object MUST fail.
            If the value of Status in the DeleteObject response is 1, the requested
            object deletion MUST be applied as soon as physically possible after
            the session has terminated, and no later than the beginning of the next
            session. Note that if a CPE requires a reboot to cause the object
            deletion to be applied, the CPE MUST initiate that reboot on its own
            after the termination of the session. Because some CPE will not require
            a reboot in these circumstances, an ACS SHOULD NOT call the Reboot
            method as a result of modifying the CPE's configuration, since this
            would result in an unnecessary reboot. Note also that if application of
            a configuration change by the CPE would result in a service disruption (
                    for example, if the CPE requires a reboot to apply the requested
                    change), it is not the responsibility of the CPE to avoid or delay such
            a disruption. To minimize the impact of such a disruption, the ACS MAY
            delay requesting such a configuration change until an appropriate time,
                  but this is entirely at the ACS's discretion. The use of the Status
                      value is independent between successive SetParameterValues, AddObject,
                  or DeleteObject requests within the same session. The use of a Status
                      value of 1 in response to one request does not necessarily imply that
                      subsequent requests in the same session will also respond in the same
                      way.
                      On deletion, all Parameters and sub-objects contained within this
                      object MUST be removed atomically. That is, either all of the
                      Parameters and sub-objects are removed together, or none are removed at
                      all. In the latter case, the CPE MUST return a fault response
                      indicating the reason for the failure to delete the object. The CPE
                      MUST NOT remove any contained Parameters or sub-objects as a result of
                      this method call without removing all of them. This requirement MUST
                      hold even if the CPE experiences a crash during the process of
                      performing the deletion.
                      All modifications to a CPE's configuration resulting from use of the
                      DeleteObject method MUST be retained across reboots of the CPE.
                      The following fault codes are defined for this method: 9001, 9002,
                  9003, 9005.
                      If the fault is caused by an invalid ObjectName value, the Invalid
                      Parameter Name fault code (9005) MUST be used instead of the more
                      general Invalid Arguments fault code (9003). The ObjectName value MUST
                      be considered invalid if it does not exactly match the name of a single
                      instance of a multi-instance object currently present in the CPE's data
                      model.";
        reference "TR-069 Appendix B";

        input {
            leaf ObjectName {
                type string {
                    length 256;
                }
                description "The path name of the object instance to be
                    removed. The path name MUST end with a '.' (dot) after the instance
                    number of the object.";
            }

            leaf ParameterKey {
                type string {
                    length 32;
                }
                description "The value to set the ParameterKey parameter.
                    The CPE MUST set ParameterKey to the value specified in this argument
                    if and only if DeleteObject completes successfully and no fault
                        response is generated. If DeleteObject does not complete successfully
                            (implying that the requested object did not get deleted), the value of
                            ParameterKey MUST NOT be modified. ParameterKey provides the ACS a
                            reliable and extensible means to track changes made by the ACS. The
                            value of this argument is left to the discretion of the ACS, and MAY be
                            left empty.";
            }
        }

        output {
            leaf Status {
                type int32 {
                    range "0..1";
                }
                description "A successful response to this method returns
                    an integer enumeration defined as follows:
                    0 = The object has been deleted.
                    1 = The object deletion has been validated and committed, but not yet
                    applied (for example, if a reboot is required before the object can be
                            deleted).";
            }
        }
    }

    // ***************************************************************

    rpc Download {
        description "This method may be used by the Server to cause the
            CPE to download a specified file from the designated location.
            When a download is initiated using this method, the CPE MUST indicate
            successful or unsuccessful completion of the download using one of the
            following three means:
            - A DownloadResponse with the Status argument having a value of zero
            (indicating success), or a fault response to the Download request
            (indicating failure).
            - A TransferComplete message sent later in the same session as the
            Download request (indicating either success or failure). In this case,
                     the Status argument in the corresponding DownloadResponse MUST have a
                         value of one.
                         - A TransferComplete message sent in a subsequent session (indicating
                                 either success or failure). In this case, the Status argument in the
                         corresponding DownloadResponse MUST have a value of one.
                         Regardless of which means is used, the CPE MUST only indicate
                         successful completion of the download after the downloaded file has
                         been both successfully transferred and applied. While the criterion
                         used to determine when a file has been successfully applied is specific
                         to the CPE's implementation, the CPE SHOULD consider a downloaded file
                         to be successfully applied only after the file is installed and in use
                         as intended.
                         In the particular case that the downloaded file is a software image,
                     the CPE MUST consider the downloaded file to be successfully applied
                         only after the new software image is actually installed and
                         operational. If the software image replaces the overall software of the
                         CPE (which would typically require a reboot to install and begin
                                 execution), the SoftwareVersion represented in the data model MUST
                         already reflect the updated software image in the session in which the
                         CPE sends a TransferComplete indicating successful download.
                         If the CPE requires a reboot to apply the downloaded file, then the
                         only appropriate means of indicating successful completion is the third
                         option listed above-a TransferComplete message sent in a subsequent
                         session.
                         If the file cannot be successfully downloaded or applied, the CPE MUST
                         NOT attempt to retry the file download on its own initiative, but
                         instead MUST report the failure of the download to the ACS using any of
                         the three means listed above. Upon the ACS being informed of the
                         failure of a download, the ACS MAY subsequently attempt to reinitiate
                         the download by issuing a new Download request.
                         If the CPE receives one or more Download requests before performing a
                         previously requested download, the CPE MUST queue all requested
                         downloads and perform each of them as closely as possible to the
                         requested time (based on the value of the DelaySeconds argument and the
                                 time of the request). Queued downloads MUST be retained across reboots
                         of the CPE. The CPE MUST be able to queue a minimum of three file
                         transfers (downloads and uploads).
                         For each download performed, the CPE MUST send a distinct
                         TransferComplete. Note that the order in which a series of requested
                         downloads will be performed might differ from the order of the
                         corresponding requests due to differing values of DelaySeconds. For
                         example, an ACS could request a download with DelaySeconds equal to one
                         hour, then five minutes later request a second download with
                         DelaySeconds equal to one minute. In this case, the CPE would perform
                         the second download before the first.
                         All modifications to a CPE's configuration resulting from use of the
                         Download method MUST be retained across reboots of the CPE.
                         The following fault codes are defined for this method: 9000, 9001,
                     9002, 9003, 9004, 9010, 9012, 9013.
                         If an attempt is made to queue an additional download when the CPE's
                         file transfer queue is already full, the CPE MUST respond with fault
                         9004 (Resources exceeded). If the CPE detects the presence of the
                         'userinfo' component in the file source URL, it SHOULD reject the
                         Download request with the fault code 9003 (Invalid arguments). If the
                         CPE rejects the Download request because the FileSize argument exceeds
                         the available space on the device, it MUST use the Download Failure
                         (9010) fault code.";

        input {
            leaf CommandKey {
                type string {
                    length 32;
                }
                description "The string the CPE uses to refer to a
                    particular download. This argument is referenced in the methods Inform,
                               TransferComplete and GetQueuedTransfers.
                                   The value of the CommandKey is entirely at the discretion of the ACS
                                   and MAY be an empty string.";
            }

            leaf FileType {
                type string {
                    length 64;
                }
                description "An integer followed by a space followed by the
                    file type description. Only the following values are currently defined
                    for the FileType argument:
                        '1 Firmware Upgrade Image'
                            '2 Web Content'
                            '3 Vendor Configuration File'
                            The following format is defined to allow the unique definition of
                            vendor-specific file types:
                            'X <OUI> <Vendor-specific identifier>'
                            <OUI> is replaced by a 6 hexadecimal-digit OUI (organizationally unique
                                    identifier) as defined in http://standards.ieee.org/faqs/OUI.html, with
                            all upper-case letters and any leading zeros included. The OUI used for
                            a given vendor-specific file type MUST be one that is assigned to the
                            organization that defined this file type (which is not necessarily the
                                    same as the vendor of the CPE or ACS).
                            If and only if the CPE supports downloading of firmware images using the
                            Download method, the CPE MUST support the '1 Firmware Upgrade Image'
                            FileType value. All other FileType values are OPTIONAL.
                            The FileType value of '2 Web Content' is intended to be used for
                            downloading files that contain only web content for a CPE's web-based
                            user interface. A CPE that supports a web-based user interface and
                            allows the content to be downloaded from the ACS via the Download
                            method as a distinct file containing only web content SHOULD use the
                            FileType value of '2 Web Content' when performing such a download. A
                            CPE that supports a web-based user interface and allows the content to
                            be downloaded from the ACS MAY instead include web content as part of
                            its firmware upgrade image, or use some other means to update the web
                            content in the CPE. Such a CPE need not support the FileType value of
                            '2 Web Content'.";
            }

            leaf URL {
                // defined as string in TR-069
                type inet:uri {
                    length  256;
                }
                description "URL, as defined in
                    http://www.ietf.org/rfc/rfc3986.txt, specifying the source file
                    location. HTTP and HTTPS transports MUST be supported. Other optional
                    transports, as specified in section 2.3.2, MAY be supported.
                    If the CPE receives multiple Download requests with the same source
                    URL, the CPE MUST perform each download as requested, and MUST NOT
                    assume that the content of the file to be downloaded is the same each
                    time.
                    This URL MUST NOT include the 'userinfo' component, as defined in
                    http://www.ietf.org/rfc/rfc3986.txt.";
                reference "TR-069 Section 2.3.2";
            }

            leaf Username {
                type string {
                    length 256;
                }
                description "Username to be used by the CPE to authenticate
                    with the file server. This string is set to the empty string if no
                    authentication is required.";
            }

            leaf Password {
                type string {
                    length 256;
                }
                description "Password to be used by the CPE to authenticate
                    with the file server. This string is set to the empty string if no
                    authentication is required.";
            }

            leaf FileSize {
                type uint32;
                units bytes;
                description "The size of the file to be downloaded in bytes.
                    The FileSize argument is intended as a hint to the CPE, which the CPE
                    MAY use to determine if it has sufficient space for the file to be
                    downloaded, or to prepare space to accept the file.
                    The ACS MAY set this value to zero. The CPE MUST interpret a zero value
                    to mean that that the ACS has provided no information about the file
                    size. In this case, the CPE MUST attempt to proceed with the download
                    under the presumption that sufficient space is available, though during
                    the course of download, the CPE might determine otherwise.
                    The ACS SHOULD set the value of this parameter to the exact size of the
                    file to be downloaded. If the value is non-zero, the CPE MAY reject the
                    Download request on the basis of insufficient space.
                    If the CPE attempts to proceed with the download based on the value of
                    this argument, but the actual file size differs from the value of this
                    argument, this could result in a failure of the download. However, the
                    CPE MUST NOT cause the download to fail solely because it determines
                    that the value of this argument is inaccurate.";
            }

            leaf TargetFileName {
                type string {
                    length 256;
                }
                description "The name of the file to be used on the target
                    file system. This argument MAY be left empty if the target file name
                    can be extracted from the downloaded file itself, or from the URL
                    argument, or if no target file name is needed. If this argument is
                    specified, but the target file name is also indicated by another source
                    (for example, if it is extracted from the downloaded file itself), this
                    argument MUST be ignored. If the target file name is used, the
                    downloaded file would replace any existing file of the same name
                    (whether or not the CPE archives the replaced file is a local matter).
                    If present, this parameter is treated as an opaque string with no
                    specific requirements for its format. That is, the TargetFileName value
                    is to be interpreted based on the CPE's vendor-specific file naming
                    conventions. Note that this specification does not preclude the use of
                    a file naming convention in which the file's path can be specified as
                    part of the file name.";
            }

            leaf DelaySeconds {
                type uint32;
                units seconds;
                description "This argument has different meanings for
                    Unicast and Multicast downloads. For Unicast downloads it is the number
                    of seconds before the CPE will initiate the download. For Multicast
                    downloads the CPE will initiate the download immediately and it is the
                    number of seconds available for initiating, performing and applying the
                    download.
                    The following applies only to Unicast downloads, i.e. to downloads
                    where the URL specifies a Unicast download transport protocol.
                    The number of seconds from the time this method is called to the time
                    the CPE is requested to initiate the download. A value of zero
                    indicates that no delay is requested. If a non-zero delay is requested,
                              the download MUST NOT occur in the same transaction session in which
                                  the request was issued. The CPE MUST perform and apply the download
                                  immediately after the time indicated by DelaySeconds, unless this is
                                  not possible for reasons outside the CPE's control, in which case the
                                  CPE MUST attempt to perform and apply the download within one hour
                                  after the time indicated by DelaySeconds. If the CPE cannot begin the
                                  download within this time window, the CPE MUST consider the download to
                                  have failed and report this failure to the ACS using the
                                  TransferComplete method. If the download completes before the end of
                                  this time window, the CPE MUST apply the download prior to the end of
                                  this time window. If the download is still in progress at the end of
                                  this time window, the CPE MUST apply the download immediately upon
                                  completion of the download.
                                  The following applies only to Multicast downloads, i.e. to downloads
                                  where the URL specifies a Multicast download transport protocol:
                                  The number of seconds from the time this method is called that are
                                  available for the CPE to initiate, perform and apply the download.
                                  Multicast downloads MUST NOT occur in the same transaction session in
                                  which the request was issued.
                                  The CPE MUST perform and apply the download immediately, unless this is
                                  not possible for reasons outside the CPE's control, in which case the
                                  CPE MUST attempt to perform and apply the download within DelaySeconds
                                  of the download request. If the CPE cannot complete the download within
                                  this time window, the CPE MUST consider the download to have failed and
                                  report this failure to the ACS using the TransferComplete method.
                                  The following applies to both Unicast and Multicast downloads:
                                  The CPE MUST attempt to perform the download within the time window
                                  specified above even if the CPE reboots one or more times prior to that
                                  time.";
            }

            leaf SuccessURL {
                // defined as string in TR-069
                type inet:uri {
                    length 256;
                }
                description "When applicable, this argument contains the
                    URL, as defined in http://www.ietf.org/rfc/rfc3986.txt, the CPE SHOULD
                    redirect the user's browser to if the download completes successfully.
                    This URL MAY include CGI arguments (for example, to maintain session
                            state).
                    This applies only if the download was initiated via browser-based user
                    interaction and the CPE supports the ability to selectively redirect
                    based on the download results.
                    When there is no need for such a URL, this argument SHOULD be empty.";
            }

            leaf FailureURL {
                // defined as string in TR-069
                type inet:uri {
                    length 256;
                }
                description "When applicable, this argument contains the
                    URL, as defined in http://www.ietf.org/rfc/rfc3986.txt, the CPE SHOULD
                    redirect the user's browser to if the download does not complete
                    successfully. This URL MAY include CGI arguments (for example, to
                            maintain session state).
                    This applies only if the download was initiated via browser-based user
                    interaction and the CPE supports the ability to selectively redirect
                    based on the download results.
                    When there is no need for such a URL, this argument SHOULD be empty.";
            }
        }

        output {
            leaf Status {
                type int32 {
                    range "0..1";
                }
                description "A successful response to this method returns
                    an integer enumeration defined as follows:
                    0 = Download has completed and been applied.
                    1 = Download has not yet been completed and applied (for example, if
                            the CPE needs to reboot itself before it can perform the file download,
                            or if the CPE needs to reboot itself before it can apply the downloaded
                            file).
                    If the value of this argument is non-zero, the CPE MUST subsequently
                    call the TransferComplete method to indicate the completion status of
                    this download (either successful or unsuccessful) either later in the
                    same session or in a subsequent session.";
            }

            leaf StartTime {
                type yang:date-and-time;
                description "The date and time download was started in UTC.
                    This need only be filled in if the download has been completed.
                    Otherwise, the value MUST be set to the Unknown Time value.";
            }

            leaf CompleteTime {
                type yang:date-and-time;
                description "The date and time the download was fully
                    completed and applied in UTC. This need only be filled in if the
                    download has been completed. Otherwise, the value MUST be set to the
                    Unknown Time value.";
            }
        }
    }

    // ***************************************************************

    rpc Reboot {
        description "This method causes the CPE to reboot, and calls
            for use of extreme caution. The CPE MUST send the method response and
                complete the remainder of the session prior to rebooting.
                    Note - Multiple invocations of this method within a single session MUST
                    result in only a single reboot. In this case the Inform following the
                    reboot would be expected to contain a single '1 BOOT' EventCode and an
                    'M Reboot' EventCode for each method invocation.
                    This method is primarily intended for troubleshooting purposes. This
                    method is not intended for use by an ACS to initiate a reboot after
                    modifying the CPE's configuration (e.g., setting CPE parameters or
                            initiating a download). If a CPE requires a reboot after its
                    configuration is modified, the CPE MUST initiate that reboot on its own
                    after the termination of the session. Because some CPE will not require
                    a reboot in these circumstances, an ACS SHOULD NOT call the Reboot
                    method as a result of modifying the CPE's configuration, since this
                    would result in an unnecessary reboot.
                    The following fault codes are defined for this method: 9001, 9002,
                        9003.";


        input {
            leaf CommandKey {
                type string {
                    length 32;
                }
                description "The string to return in the CommandKey element
                    of the InformStruct when the CPE reboots and calls the Inform method.
                    The value of the CommandKey is entirely at the discretion of the ACS
                    and MAY be an empty string.";
            }
        }

        // No output arguments, therefore omitted
        // output {}
    }

    // ***************************************************************
    // optional CPE RPC methods
    // ***************************************************************

    rpc GetQueuedTransfers {
        description "Note - this method is DEPRECATED in favor of
            GetAllQueuedTransfers.
            This method MAY be used by an ACS to determine the status of previously
            requested downloads or uploads.
            The following fault codes are defined for this method: 9000, 9001,
                9002.";
        status deprecated;

        // this method has no calling arguments
        // input { }

        output {

            list TransferList {
                description "Array of structures as defined in
                    QueuedTransferStruct, each describing the state of one transfer that
                    the CPE has been instructed to perform, but has not yet been fully
                    completed.";
                key CommandKey;
                max-elements 16;

                leaf CommandKey {
                    type string {
                        length 32;
                    }
                    description "Set to the value of the CommandKey argument
                        passed to CPE in the Download or Upload method call that initiated the
                        transfer.";
                }

                leaf State {
                    type int32 {
                        range "1..3";
                    }
                    description "The current state of the transfer.
                        Defined values are:
                        1 = Not yet started
                        2 = In progress
                        3 = Completed, finishing cleanup
                        All other values are reserved.";
                }
            }
        }
    } // rpc GetQueuedTransfers

    // ***************************************************************

    rpc ScheduleInform {
        description "This method MAY be used by a ACS to request the
            CPE to schedule a one-time Inform method call (separate from its
                    periodic Inform method calls) sometime in the future.
            The following fault codes are defined for this method: 9000, 9001,
                9002, 9003.";


        input {
            leaf DelaySeconds {
                type uint32 {
                    range "1..max";
                }
                units seconds;
                description "The number of seconds from the time this
                    method is called to the time the CPE is requested to intiate a one-time
                    Inform method call. The CPE sends a response, and then DelaySeconds
                    later calls the Inform method. This argument must be greater than
                    zero.";
            }

            leaf CommandKey {
                type string {
                    length 32;
                }
                description "The string to return in the CommandKey
                    element of the InformStruct when the CPE calls the Inform method.
                    The value of the CommandKey is entirely at the discretion of the ACS
                    and MAY be an empty string.";
            }
        }

        // method has no output arguments
        // output { }

    } // rpc ScheduleInform

    // ***************************************************************

    rpc SetVouchers {
        description "This method MAY be used by an ACS to set one or
            more option Vouchers in the CPE.
            The following fault codes are defined for this method: 9000, 9001,
                9002, 9003, 9004.";

        input {
            leaf-list Voucherlist {
                // base64!
                type binary;
                description "Array of Vouchers, where each Voucher is
                    represented as a Base64 encoded octet string.
                    The detailed structure of a Voucher is defined in Annex C.";
                reference "TR-069 Amandment 2 Annex C";
            }
        }

        // method has no output arguments
        // output { }

    } // rpc SetVouchers

    // ***************************************************************

    rpc GetOptions {
        description "This method MAY be used by an ACS to obtain a list
            of the options currently set in a CPE, and their associated state
            information.
            The following fault codes are defined for this method: 9000, 9001,
                9002, 9003.";

        input {
            leaf OptionName {
                type string {
                    length 64;
                }
                description "A string representing either the name of a
                    particular Option, or an empty string indicating the method SHOULD
                    return the state of all Options supported by the CPE (whether or not
                            they are currently enabled).";
            }
        }

        output {

            list OptionList {
                description "Array of OptionStructs as defined in
                    OptionStruct, containing either a single OptionStruct if information
                    about a particular Option was requested, or a list of OptionStructs,
                          one for each option supported by the CPE.";
                key OptionName;

                leaf OptionName {
                    type string {
                        length 64;
                    }
                    description "Identifying name of the particular Option.";
                }

                leaf VoucherSN {
                    type uint32;
                    description "Identifying number of the particular Option.";
                }

                leaf State {
                    type uint32;
                    description "A number formed by two bits, defined as follows:
                        Bit 0 (LSB):
                            0 = Option is currently disabled
                            1 = Option is currently enabled
                            Bit 1:
                            0 = Option has not been setup
                            1 = Option has been setup
                            The interpretation of the setup state of an Option is Option-specific,
                            but in general is to be interpreted as indicating whether the end-user
                            has actively performed any actions required to make the Option fully
                            operational.";
                }

                leaf Mode {
                    type int32 {
                        range "0..2";
                    }
                    description "This element specifies whether the designated
                        Option is enabled or disabled; and if enabled, whether or not an
                        expiration has been specified. The defined values are:
                        0 = Disabled
                        1 = Enabled with expiration
                        2 = Enabled without expiration";
                }

                leaf StartDate {
                    type yang:date-and-time;
                    description "The specified start date for the Option in UTC.
                        If in the future, this is the date the Option is to be enabled. If in
                        the past, this is the date the Option was enabled.
                        This element applies only when the value of the Mode element is 1
                        (Enabled with expiration). When the Mode element has any other value,
                        StartDate MUST be set to the Unknown Time value.";
                }

                leaf ExpirationDate {
                    type yang:date-and-time;
                    description "The specified date the Option is to expire in
                        UTC, if any.
                        This element applies only when the value of the Mode element is 1
                        (Enabled with expiration). When the Mode element has any other value,
                        ExpirationDate MUST be set to the Unknown Time value.";
                }

                leaf IsTransferable {
                    type boolean;
                    description "Indicates whether or not the Option has been
                        designated transferable or non-transferable (see Annex C).
                        Defined values are:
                        0 = Non-transferable
                        1 = Transferable";
                    reference "TR-069 Annex C";
                }
            } // list
        }
    } // rpc GetOptions

    // ***************************************************************

    rpc Upload {
        description "This method MAY be used by the ACS to cause the
            CPE to upload a specified file to the designated location.
            If the file cannot be successfully uploaded, the CPE MUST NOT attempt
            to retry the file upload on its own initiative, but instead MUST report
            the failure of the upload to the ACS via either the Upload response (if
                    it has not yet been sent) or the TransferComplete method. Upon the ACS
            being informed of the failure of an upload, the ACS MAY subsequently
            attempt to reinitiate the upload by issuing a new Upload request.
            If the CPE receives one or more Upload requests before performing a
            previously requested upload, the CPE MUST queue all requested uploads
            and perform each of them as closely as possible to the requested time
            (based on the value of the DelaySeconds argument and the time of the
             request). Queued uploads MUST be retained across reboots of the CPE.
            The CPE MUST be able to queue a minimum of three file transfers
            (downloads and uploads).
            For each upload performed, the CPE MUST send a distinct
            TransferComplete. Note that the order in which a series of requested
            uploads will be performed might differ from the order of the
            corresponding requests due to differing values of DelaySeconds. For
            example, an ACS could request an upload with DelaySeconds equal to one
            hour, then five minutes later request a second upload with DelaySeconds
            equal to one minute. In this case, the CPE would perform the second
            upload before the first.
            The following fault codes are defined for this method: 9000, 9001,
                9002, 9003, 9004, 9011, 9012, 9013.
                    If an attempt is made to queue an upload when the file transfer queue
                    is already full, the CPE MUST respond with fault 9004 (Resources
                            exceeded). If the CPE detects the presence of the 'userinfo' component
                    in the file destination URL, it SHOULD reject the Upload request with
                    the fault code 9003 (Invalid arguments).";

        input {
            leaf CommandKey {
                type string {
                    length 32;
                }
                description "The string the CPE uses to refer to a
                    particular upload. This argument is referenced in the methods
                    TransferComplete and GetQueuedTransfers.
                    The value of the CommandKey is entirely at the discretion of the ACS
                    and MAY be an empty string.";
            }

            leaf FileType {
                type string {
                    length 64;
                }
                description "An integer followed by a space followed by the
                    file type description. Only the following values are currently defined
                    for the FileType argument:
                        '1 Vendor Configuration File'
                            '2 Vendor Log File'
                            The following format is defined to allow the unique definition of
                            vendor-specific file types:
                            'X <OUI> <Vendor-specific identifier>'
                            <OUI> is replaced by a 6 hexadecimal-digit OUI (organizationally unique
                                    identifier) as defined in http://standards.ieee.org/faqs/OUI.html, with
                            all upper-case letters and any leading zeros included. The OUI used for
                            a given vendor-specific file type MUST be one that is assigned to the
                            organization that defined this file type (which is not necessarily the
                                    same as the vendor of the CPE or ACS).
                            The FileType argument is intended to fully identify the file to be
                            uploaded. If the standard values listed above are insufficient to
                            uniquely identify the file, then vendor-specific file types MAY be used
                            that provide more specific information to allow the intended file to be
                            identified.";
            }

            leaf URL {
                // defined as string in TR-069
                type inet:uri {
                    length 256;
                }
                description "URL, as defined in
                    http://www.ietf.org/rfc/rfc3986.txt, specifying the destination file
                    location. HTTP and HTTPS transports MUST be supported. Other optional
                    transports, as specified in section 2.3.2, MAY be supported. When
                    performing an upload to the URL specified by this argument, the CPE
                    MUST make use of the HTTP PUT method.
                    This argument specifies only the destination file location, and does
                    not indicate in any way the name or location of the local file to be
                    uploaded. The local file to be uploaded MUST be determined only by the
                    FileType argument.
                    This URL MUST NOT include the 'userinfo' component, as defined in
                    http://www.ietf.org/rfc/rfc3986.txt.
                    The following fault codes are defined for this method: 9000, 9001,
                        9002, 9003, 9004, 9011, 9012, 9013.
                            If an attempt is made to queue an upload when the file transfer queue
                            is already full, the CPE MUST respond with fault 9004 (Resources
                                    exceeded). If the CPE detects the presence of the 'userinfo' component
                            in the file destination URL, it SHOULD reject the Upload request with
                            the fault code 9003 (Invalid arguments).";
            }

            leaf Username {
                type string {
                    length 256;
                }
                description "Username to be used by the CPE to authenticate
                    with the file server. This string is set to the empty string if no
                    authentication is required.";
            }

            leaf Password {
                type string {
                    length 256;
                }
                description "Password to be used by the CPE to authenticate
                    with the file server. This string is set to the empty string if no
                    authentication is required.";
            }

            leaf DelaySeconds {
                type uint32;
                units seconds;
                description "The number of seconds from the time this
                    method is called to the time the CPE is requested to initiate the
                    upload. A value of zero indicates that no delay is requested. If a non-
                    zero delay is requested, the upload MUST NOT occur in the same
                    transaction session in which the request was issues.
                    The CPE MUST perform the upload immediately after the time indicated by
                    DelaySeconds, unless this is not possible for reasons outside the CPE's
                    control, in which case the CPE MUST attempt to perform the upload
                    within one hour after the time indicated by DelaySeconds. If the CPE
                    cannot begin the upload within this time window, the CPE MUST consider
                    the upload to have failed and report this failure to the ACS using the
                    TransferComplete method. The CPE MUST attempt to perform the upload
                    within the time window specified above even if the CPE reboots one or
                    more times prior to that time.";
            }
        } // input

        output {
            leaf Status {
                type int32 {
                    range "0..1";
                }
                description "A successful response to this method returns
                    an integer enumeration defined as follows:
                    0 = Upload has completed.
                    1 = Upload has not yet completed (for example, if the upload needs to
                            wait until after the session has been terminated).
                    If the value of this argument is non-zero, the CPE MUST subsequently
                    call the TransferComplete method to indicate the completion status of
                    this upload (either successful or unsuccessful) either later in the
                    same session or in a subsequent session.";
            }

            leaf StartTime {
                type yang:date-and-time;
                description "The date and time upload was started in UTC.
                    This need only be filled in if the upload has been completed.
                    Otherwise, the value MUST be set to the Unknown Time value.";
            }

            leaf CompleteTime {
                type yang:date-and-time;
                description "The date and time the upload was fully
                    completed and applied in UTC. This need only be filled in if the upload
                    has been completed. Otherwise, the value MUST be set to the Unknown
                    Time value.";
            }
        }
    } // rpc Upload

    // ***************************************************************

    rpc FactoryReset {
        description "This method resets the CPE to its factory default
            state, and calls for use with extreme caution. The CPE MUST initiate
            the factory reset procedure only after successful completion of the
            session.
            The following fault codes are defined for this method: 9000, 9001,
                9002, 9003.";

        // this method has neither input nor output parameters
        // input { }
        // output { }

    } // rpc FactoryReset

    // ***************************************************************

    rpc GetAllQueuedTransfers {
        description "This method MAY be used by an ACS to determine the
            status of all queued downloads and uploads, including any that were not
            specifically requested by the ACS, i.e. autonomous transfers.";

        // empty -> omitted
        // input { }

        output {

            list TransferList {
                description "Array of structures as defined in Table
                    AllQueuedTransferStruct, each describing the state of one transfer that
                    has not yet been fully completed.";
                key CommandKey;
                max-elements 16;

                leaf CommandKey {
                    type string {
                        length 32;
                    }
                    description "Set to the value of the CommandKey argument
                        passed to CPE in the Download or Upload method call that initiated the
                        transfer, or an empty string for an autonomous transfer.";
                }

                leaf State {
                    type int32 {
                        range "1..3";
                    }
                    description "The current state of the transfer.
                        Defined values are:
                        1 = Not yet started
                        2 = In progress
                        3 = Completed, finishing cleanup
                        All other values are reserved.";
                }

                leaf IsDownload {
                    type boolean;
                    description "Indicates whether the transfer is a download
                        (true) or an upload (false).";
                }

                leaf FileType {
                    type string {
                        length 64;
                    }
                    description "An integer followed by a space followed by the
                        file type description. Only the following values are currently defined
                        for the FileType argument:
                            '1 Firmware Upgrade Image' (download only)
                                '2 Web Content' (download only)
                                '3 Vendor Configuration File' (download or upload)
                                '4 Vendor Log File' (upload only)
                                The following format is defined to allow the unique definition of
                                vendor-specific file types:
                                'X <OUI> <Vendor-specific identifier>'
                                <OUI> is replaced by a 6 hexadecimal-digit OUI (organizationally unique
                                        identifier) as defined in http://standards.ieee.org/faqs/OUI.html, with
                                all upper-case letters and any leading zeros included. The OUI used for
                                a given vendor-specific file type MUST be one that is assigned to the
                                organization that defined this file type (which is not necessarily the
                                        same as the vendor of the CPE or ACS).";
                }

                leaf FileSize {
                    type uint32;
                    units bytes;
                    description "The size of the file in bytes, or zero if this
                        information is not available or if the CPE chooses not to make it
                        available.";
                }

                leaf TargetFileName {
                    type string {
                        length 256;
                    }
                    description "The name of the file on the target (CPE) file
                        system, or an empty string if this information is not available or if
                        the CPE chooses not to make it available.";
                }
            }
        }
    } // rpc GetAllQueuedTransfers

} // submodule
