module Device.RPC.Structs {

    yang-version 1;

    namespace "urn:telekom:tr181:device:2:rpc:structs";

    prefix "RPCStr";

    import ietf-yang-types {prefix yang;}

    organization "Deutsche Telekom AG";

    contact 
        'Web:   <http://opencpe.org/contact>
Email: OpenCPE Support
       <mailto:support@opencpe.org>';

    description
        'Copyright (c) 2013 Deutsche Telekom AG

This module models structs that are used by the TR-069 data model RPC methods.
';

    revision "2013-09-22" {
        description "Version 0.1.0 -- Initial release";
    }

    // *****************************************************************
    // groupings substituting structs in RPC methods
    // *****************************************************************

    grouping ParameterValueStruct {
        list ParameterList {
            key Name;
            leaf Name {
                type string {
                    length 256;
                }
                description "This is the name of a Parameter. The CPE MUST
                    treat the parameter name as case sensitive.";
            }

            anyxml Value {
                description "This is the value the Parameter is to be set.";
            }
        }
    }

    // *****************************************************************

    grouping ParameterInfoStruct {
        list ParameterList {
            key Name;
            leaf Name {
                type string {
                    length 256;
                }
                description "This is the name of a Parameter or partial path
                    name.";
            }

            leaf Writable {
                type boolean;
                description "Whether or not the Parameter value can be
                    overwritten using the SetParameterValues method.
                    If Name is a partial path that refers to an object, this indicates
                    whether or not AddObject can be used to add new instances of this
                    object.
                    If Name is a partial path that refers to a particular instance of a
                    multi-instance object, this indicates whether or not DeleteObject can
                    be used to remove this particular instance.
                    This element MUST be true only if the corresponding Parameter or object
                    as implemented in this CPE is writable as described above. The value of
                    this element MUST reflect only the actual implementation rather than
                    whether or not the specification of the Parameter or object allows it
                    to be writable.";
            }
        }
    }

    // *****************************************************************

    grouping SetParameterAttributesStruct {
        list ParameterList {
            key Name;
            leaf Name {
                type string {
                    length 256;
                }
                description "This is the name of a Parameter to apply the new
                    attributes. Alternatively, this MAY be a partial path name, indicating
                    that the new attributes are to be applied to all Parameters below this
                    point in the naming hierarchy. For such Parameters within multi-
                    instance objects where the instance number is below the specified point
                    in the naming hierarchy, the specified attribute values MUST only be
                    applied within instances that exist at the time this method is invoked.
                    A partial path name MUST end with a “.” (dot) after the last node name
                    in the hierarchy. An empty string indicates the top of the name
                    hierarchy.
                    Below is an example of a full Parameter name:
                    InternetGatewayDevice.DeviceInfo.SerialNumber
                    Below is an example of a partial path name:
                    InternetGatewayDevice.DeviceInfo.";
            }

            leaf NotificationChange {
                type boolean;
                description "If true, the value of Notification replaces the
                    current notification setting for this parameter or group of parameters.
                    If false, no change is made to the notification setting.";
            }

            leaf Notification {
                type int32 {
                    range "0..2";
                }
                description "Indicates whether the CPE will include changed
                    values of the specified parameter(s) in the Inform message, and whether
                    the CPE will initiate a session to the ACS when the specified
                    parameter(s) change in value. The following values are defined:
                    0 = Notification off. The CPE need not inform the ACS of a change to
                    the specified parameter(s).
                    1 = Passive notification. Whenever the specified parameter value
                    changes, the CPE MUST include the new value in the ParameterList in the
                    Inform message that is sent the next time a session is established to
                    the ACS. If the CPE has rebooted, or the URL of the ACS has changed
                    since the last session, the CPE MAY choose not to include the list of
                    changed parameters in the first session established with the new ACS.
                    2 = Active notification. Whenever the specified parameter value
                    changes, the CPE MUST initiate a session to the ACS, and include the
                    new value in the ParameterList in the associated Inform message. For
                    parameters defined in the corresponding data model as requiring Forced
                    Active Notification, the value of the Notification attribute is
                    irrelevant and an attempt to set it to a value other than 2 will be
                    ignored. Whenever a parameter change is sent in the Inform message due
                    to a non-zero Notification setting, the Event code '4 VALUE CHANGE'
                    MUST be included in the list of Events. Note that if the CPE deletes
                    an object containing parameters for which Notification is enabled
                    (active or passive), this MUST NOT be considered a value-change for
                    the purpose of Notification. By default, prior to any changes to this
                    attribute by an ACS, its value SHOULD be 0 (Notification off) unless
                    otherwise specified in the appropriate data model definition. The CPE
                    MAY provide no support for Active Notification on a parameter deemed
                    inappropriate for Active Notification. A parameter is deemed
                    inappropriate for Active Notification if and only if that parameter is
                    explicitly defined as such in the definition of the corresponding data
                    model. Parameters that might be deemed inappropriate for Active
                    Notification include parameters that change frequently, such as
                    statistics. A CPE MUST accept a request to enable Passive Notification
                    for any parameter. Note that if a CPE implementation does not allow a
                        particular parameter value to change in a manner that would result in a
                            Notification (e.g., a capability flag that could only change as a
                                    result of a firmware update that requires a reboot, or a writeable
                                    parameter that can only be modified via the CPE WAN Management
                                    Protocol), then support for Notification for this parameter involves no
                            more than keeping track of the value of its Notification attribute.
                            For such a parameter, the CPE implementation need not incorporate a
                            mechanism to detect value changes nor to initiate Notifications based
                            on such changes.";
            }

            leaf AccessListChange {
                type boolean;
                description "If true, the value of AccessList replaces the
                    current access list for this parameter or group of parameters.
                    If false, no change is made to the access list.";
            }

            leaf-list AccessList {
                type string {
                    length 64;
                }
                description "Array of zero or more entities for which write
                    access to the specified Parameter(s) is granted. If there are no
                    entries, write access is only allowed from an ACS.
                    At present, only one type of entity is defined that can be included in
                    this list: 'Subscriber' Indicates write access by an interface
                    controlled on the subscriber LAN. Includes any and all such LAN-side
                    mechanisms, which MAY include but are not limited to TR-064 (LAN-side
                            DSL CPE Configuration Protocol), UPnP, the device’s user interface,
                    client-side telnet, and client-side SNMP.
                        Currently, access restrictions for other WAN-side configuration
                        protocols is not specified. The ACS MAY further specify management
                        entities in the ACL using a vendor-specific prefix. If such entities
                        are specified by vendors, they MUST be preceded by X_<VENDOR>_and
                        follow the syntax for vendor extensions for parameter names defined in
                        TR-106 Amendment 1, Data Model Template for TR-069-Enabled Devices,
                    Broadband Forum Technical Report.
                        The CPE MUST correctly interpret the value 'Subscriber' as described
                        above, but MUST ignore any other individual values in this array that
                        it does not understand.
                        By default, prior to any changes to the access list by an ACS, access
                        SHOULD be granted to all entities specified above.
                        The TR-069 ACS always has write access to all writeable parameters
                        regardless of being on the access list. Other entities have write
                        access only if they appear on the access list. An entity that is
                        restricted from write access to a certain parameter MUST NOT be allowed
                        to change parameter values and MUST NOT be allowed to delete objects
                        within which the parameter is contained. The TR-069 access control
                        mechanism does not prevent any entity from creating new object
                        instances.
                        The CPE MUST accept changes to the AccessList for any Parameter even if
                        that Parameter is read-only and its value cannot be modified by any
                        management entity. For such read-only Parameters, the CPE MUST store
                        the modified AccessList value and return it when requested via
                        GetParameterAttributes, but MAY otherwise ignore this value.";
            }
        }
    }

    // *****************************************************************

    grouping ParameterAttributesStruct {
        list ParameterList {
            key Name;
            leaf Name {
                type string {
                    length 256;
                }
                description "This is the name of a Parameter to which the
                    attributes are given.The Name MUST be a full Parameter name, and MUST
                    NOT be a partial path.";
            }

            leaf Notification {
                type int32 {
                    range "0..2";
                }
                description "Indicates whether the CPE will include changed
                    values of the specified parameter(s) in the Inform message, and whether
                    the CPE will initiate a session to the ACS when the specified
                    parameter(s) change in value. The following values are defined:
                    0 = Notification off. The CPE need not inform the ACS of a change to
                    the specified parameter(s).
                    1 = Passive notification. Whenever the specified parameter value
                    changes, the CPE MUST include the new value in the ParameterList in the
                    Inform message that is sent the next time a session is established to
                    the ACS.
                    2 = Active notification. Whenever the specified parameter value
                    changes, the CPE MUST initiate a session to the ACS, and include the
                    new value in the ParameterList in the associated Inform message.";
            }

            leaf-list  AccessList {
                type string {
                    length 64;
                }
                description "Array of zero or more entities for which write
                    access to the specified Parameter(s) is granted. If there are no
                    entries, write access is only allowed from an ACS. At present, only one
                    type of entity is defined that can be included in this list:
                    'Subscriber' Indicates write access by an interface controlled on the
                    subscriber LAN. Includes any and all such LAN-side mechanisms, which MAY
                    include but are not limited to TR-064 (LAN-side DSL CPE Configuration
                            Protocol), UPnP, the device’s user interface, client-side telnet, and
                    client-side SNMP.
                    The list MAY include vendor-specific entities, which MUST be preceded
                    by X_<VENDOR>_and follow the syntax for vendor extensions for parameter
                    names defined in TR-106 Amendment 1, Data Model Template for TR-069-
                    Enabled Devices, Broadband Forum Technical Report.
                    The ACS MAY ignore any individual items in this array that it does not
                    understand.
                    By default, prior to any changes to the access list by an ACS, the
                    AccessList attribute for all parameters SHOULD include all entities
                    that the CPE supports, indicating access granted to all of these
                    entities.";
            }
        }
    }

    // *****************************************************************

    grouping QueuedTransferStruct {
        list TransferList {

            key CommandKey;
            max-elements 16;

            leaf CommandKey {
                type string {
                    length 32;
                }
                description "Set to the value of the CommandKey argument
                    passed to CPE in the Download or Upload method call that initiated the
                    transfer.";
            }

            leaf State {
                type int32 {
                    range "1..3";
                }
                description "The current state of the transfer.
                    Defined values are:
                    1 = Not yet started
                    2 = In progress
                    3 = Completed, finishing cleanup
                    All other values are reserved.";
            }
        }
    } // grouping QueuedTransferStruct

    // *******************************************************

    grouping OptionStruct{
        list OptionList {
            key OptionName;

            leaf OptionName {
                type string {
                    length 64;
                }
                description "Identifying name of the particular Option.";
            }

            leaf VoucherSN {
                type uint32;
                description "Identifying number of the particular Option.";
            }

            leaf State {
                type uint32;
                description "A number formed by two bits, defined as follows:
                    Bit 0 (LSB):
                        0 = Option is currently disabled
                        1 = Option is currently enabled
                        Bit 1:
                        0 = Option has not been setup
                        1 = Option has been setup
                        The interpretation of the setup state of an Option is Option-specific,
                        but in general is to be interpreted as indicating whether the end-user
                        has actively performed any actions required to make the Option fully
                        operational.";
            }

            leaf Mode {
                type int32 {
                    range "0..2";
                }
                description "This element specifies whether the designated
                    Option is enabled or disabled; and if enabled, whether or not an
                    expiration has been specified. The defined values are:
                    0 = Disabled
                    1 = Enabled with expiration
                    2 = Enabled without expiration";
            }

            leaf StartDate {
                type yang:date-and-time;
                description "The specified start date for the Option in UTC.
                    If in the future, this is the date the Option is to be enabled. If in
                    the past, this is the date the Option was enabled.
                    This element applies only when the value of the Mode element is 1
                    (Enabled with expiration). When the Mode element has any other value,
                    StartDate MUST be set to the Unknown Time value.";
            }

            leaf ExpirationDate {
                type yang:date-and-time;
                description "The specified date the Option is to expire in
                    UTC, if any.
                    This element applies only when the value of the Mode element is 1
                    (Enabled with expiration). When the Mode element has any other value,
                    ExpirationDate MUST be set to the Unknown Time value.";
            }

            leaf IsTransferable {
                type boolean;
                description "Indicates whether or not the Option has been
                    designated transferable or non-transferable (see Annex C).
                    Defined values are:
                    0 = Non-transferable
                    1 = Transferable";
                reference "TR-069 Annex C";
            }
        } // list
    } // grouping OptionStruct

    // *****************************************************************

    grouping ArgStruct {
        list ArgStruct {

            key Name;

            leaf Name {
                type string {
                    length 64;
                }
                description "Argument name.";
            }

            leaf Value {
                type string {
                    length 256;
                }
                description "Argument value.";
            }
            max-elements 16;
        } // list
    } // grouping ArgStruct

    // *****************************************************************

    grouping AllQueuedTransferStruct {
        list TransferList {
            key CommandKey;
            max-elements 16;

            leaf CommandKey {
                type string {
                    length 32;
                }
                description "Set to the value of the CommandKey argument
                    passed to CPE in the Download or Upload method call that initiated the
                    transfer, or an empty string for an autonomous transfer.";
            }

            leaf State {
                type int32 {
                    range "1..3";
                }
                description "The current state of the transfer.
                    Defined values are:
                    1 = Not yet started
                    2 = In progress
                    3 = Completed, finishing cleanup
                    All other values are reserved.";
            }

            leaf IsDownload {
                type boolean;
                description "Indicates whether the transfer is a download
                    (true) or an upload (false).";
            }

            leaf FileType {
                type string {
                    length 64;
                }
                description "An integer followed by a space followed by the
                    file type description. Only the following values are currently defined
                    for the FileType argument:
                        '1 Firmware Upgrade Image' (download only)
                            '2 Web Content' (download only)
                            '3 Vendor Configuration File' (download or upload)
                            '4 Vendor Log File' (upload only)
                            The following format is defined to allow the unique definition of
                            vendor-specific file types:
                            'X <OUI> <Vendor-specific identifier>'
                            <OUI> is replaced by a 6 hexadecimal-digit OUI (organizationally unique
                                    identifier) as defined in http://standards.ieee.org/faqs/OUI.html, with
                            all upper-case letters and any leading zeros included. The OUI used for
                            a given vendor-specific file type MUST be one that is assigned to the
                            organization that defined this file type (which is not necessarily the
                                    same as the vendor of the CPE or ACS).";
            }

            leaf FileSize {
                type uint32;
                units bytes;
                description "The size of the file in bytes, or zero if this
                    information is not available or if the CPE chooses not to make it
                    available.";
            }

            leaf TargetFileName {
                type string {
                    length 256;
                }
                description "The name of the file on the target (CPE) file
                    system, or an empty string if this information is not available or if
                    the CPE chooses not to make it available.";
            }
        }
    } // grouping AllQueuedTransferStruct

    // *****************************************************************

    grouping DeviceIdStruct {
        container DeviceId {
            leaf Manufacturer {
                type string {
                    length 64;
                }
                description "Manufacturer of the device (for display
                    only).";
            }

            leaf OUI {
                type string {
                    length 6;
                    pattern "[A-F0-9]{6}";
                }
                description "Organizationally unique identifier of the
                    device manufacturer. Represented as a six hexadecimal-digit value using
                    all upper-case letters and including any leading zeros. The value MUST
                    be a valid OUI as defined in http://standards.ieee.org/faqs/OUI.html.";
            }

            leaf ProductClass {
                type string {
                    length 64;
                }
                description "Identifier of the class of product for which
                    the serial number applies. That is, for a given manufacturer, this
                    parameter is used to identify the product or class of product over
                    which the SerialNumber parameter is unique.";
            }

            leaf SerialNumber {
                type string {
                    length 64;
                }
                description "Identifier of the particular device that is
                    unique for the indicated class of product and manufacturer.";
            }
        }
    } // grouping DeviceIdStruct

    // *******************************************************************

    grouping EventStruct {
        container Event {

            leaf EventCode {
                type string {
                    length 64;
                }
                description "Each value consists of an identifying
                    character followed by a text description of the cause. Several specific
                    cause values are listed below, as well as a syntax for specifying
                    vendor-specific causes.
                    Value Cause
                    '0 BOOTSTRAP' Indicates that the session was
                    established due to first-time CPE
                    installation or a change to the ACS
                    URL.
                    '1 BOOT' Indicates that the session was
                    established due to the CPE being
                    powered up or reset. This includes
                    initial system boot, as well as reboot
                    due to any cause, including use of the
                    Reboot method.
                    '2 PERIODIC' Indicates that the session was
                    established on a periodic Inform
                    interval.
                    '3 SCHEDULED' Indicates that the session was
                    established due to a ScheduleInform
                    method call.
                    '4 VALUE CHANGE' Indicates that the session was
                    established due to a change to one of
                    the Parameter values included in the
                    Inform method call. For example, the
                    allocation of a new IP address to the
                    CPE.
                    '5 KICKED' Indicates that the session was
                    established for the purpose of web
                    identity management (see Appendix D)
                    and that a Kicked method (see section
                            A.4.2.1) will be issued during this
                    session.
                    '6 CONNECTION Indicates that the session was
                    REQUEST'    established due to a Connection
                    Request notification from the Server as
                    described in section 3.2.
                    '7 TRANSFER Indicates that the session was
                    COMPLETE' established to indicate the completion
                    of a previously requested download or
                    upload (either successful or
                            unsuccessful) and that the
                    TransferComplete method will be
                    called one or more times during this
                    session.
                    '8 DIAGNOSTICS Used when reestablishing a
                    COMPLETE'      connection to the ACS after completing
                    a diagnostic test initiated by the ACS.
                    For example, the DSL loop diagnostics
                    (see Appendix B).
                    'M '<method name> If this results from another method, the
                    value is a 'M' followed by a space and
                    the method name.
                    For example:
                    'M Reboot'
                    'X '<OUI> <event> Vendor-specific event. The OUI after
                    the 'X' and space is an
                    organizationally unique identifier
                    represented as a six hexadecimal-digit
                    value using all upper-case letters and
                    including any leading zeros. The value
                    MUST be a valid OUI as defined in [9].
                    The value and interpretation of
                    <event> is vendor-specific.
                    For example:
                    'X 00D09E MyEvent'";
            }

            leaf CommandKey {
                type string {
                    length 32;
                }
                description "If the EventCode in this Event list entry
                    corresponds to a cause in which a CommandKey has been specified, this
                    element MUST contain the value of that CommandKey.
                    For this version of the specification, the following causes result in
                    this argument being set to the value of the CommandKey argument in the
                    originating method call:
                    • ScheduledInform method (EventCode = 'M ScheduleInform')
                    • Reboot method (EventCode = 'M Reboot')
                    • Download method (EventCode = 'M Download')
                    • Upload method (EventCode = 'M Upload')
                    For each of the above methods, the CommandKey value from the method
                    argument MUST appear in the Event array entry containing the EventCode
                    value shown above. For all other EventCode values defined in this
                    specification, the value of CommandKey MUST be an empty string.";
            }
        }
    } // grouping EventStruct

    // *************************************************************

    grouping FaultStruct {
        container FaultStruct{
            leaf Faultcode {
                type uint32;
                description "The numerical fault code as defined in section
                    A.5.1. In the case of a fault, allowed values are: 9001, 9002, 9010,
                    9011, 9012, 9014, 9015, 9016, 9017, 9018, 9019. A value of 0 (zero)
                        indicates no fault.";
            }

            leaf FaultString {
                type string {
                    length 256;
                }
                description "A human-readable text description of the fault.
                    This field SHOULD be empty if the FaultCode equals 0 (zero).";
            }
        }
    } // grouping FaultStruct


} // module
