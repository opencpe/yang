module Device.RPC {

    yang-version 1;

    namespace "urn:telekom:tr181:device:2:rpc";

    prefix Device.RPC;

    include Device.RPC.CPE;

    organization "Deutsche Telekom AG";

    contact 
        'Web:   <http://opencpe.org/contact>
Email: OpenCPE Support
       <mailto:support@opencpe.org>';

    description
        'Copyright (c) 2013 Deutsche Telekom AG

This module models baseline RPC methods for the TR-069 Amandment 2 data model. The methods are required to be supported on both CPE and Servers. Either a CPE or a Server can call these methods.
';

    revision "2013-09-22" {
        description "Version 0.1.0 -- Initial release";
    }


    // *****************************************************************
    // baseline RPC methods
    // *****************************************************************

    rpc GetRPCMethods {
        description "This method MAY be used by a CPE or ACS to
            discover the set of methods supported by the ACS or CPE it is in
            communication with. This list MUST include all the supported methods,
                          both standard methods (those defined in this specification or a
                                  subsequent version) and vendor-specific methods. The receiver of the
                              response MUST ignore any unrecognized methods.
                              Vendor-specific methods MUST be in the form X_<VENDOR>_MethodName,
                          where <VENDOR> is a unique vendor identifier, which MAY be either an
                              OUI or a domain name. The OUI or domain name used for a given vendor-
                              specific method MUST be one that is assigned to the organization that
                              defined this method (which is not necessarily the same as the vendor of
                                      the CPE or ACS). An OUI is an organizationally unique identifier as
                              defined in http://standards.ieee.org/faqs/OUI.html, which MUST
                              formatted as a 6 hexadecimal-digit OUI (organizationally unique
                                      identifier), with all upper-case letters and any leading zeros included.
                              A domain name MUST be upper case with each dot ('.') replaced with a
                              hyphen or underscore. Examples: X_012345_MyMethod, X_ACME_COM_MyMethod.

                              The following fault codes are defined for this method for response from
                              a CPE: 9001, 9002.
                              The following fault codes are defined for this method for response from
                              an ACS: 8001, 8002, 8005.";

        // the input statement is optional and has no nodes under it
        // in the GetRPCMethods method so it is omitted.
        // input { }

        output {
            leaf-list MethodList {
                type string {
                    length "0..64";
                }
                description "Array of strings containing the names of each
                    of the RPC methods the recipient supports. The list of methods returned
                    by an ACS MUST always include 'Inform'.
                    For example, a CPE implementing only the baseline methods defined in
                    this version of the specification would return the following list when
                    requested by an ACS:
                    'GetRPCMethods'
                    'SetParameterValues'
                    'GetParameterValues'
                    'GetParameterNames'
                    'SetParameterAttributes'
                    'GetParameterAttributes'
                    'AddObject'
                    'DeleteObject'
                    'Reboot'
                    'Download'
                    As another example, an ACS implementing only the baseline methods
                    defined in this version of the specification would return the following
                    list when requested by a CPE:
                    'Inform'
                    'GetRPCMethods'
                    'TransferComplete'";
            }
        }
    }

} // module
