module homegateway-firmware-mgmt {

    namespace "urn:homegateway:firmware-mgmt";

    prefix "hg-fw-mgmt";

    // import statements here: e.g.,

    import ietf-inet-types {
        prefix "inet";
        revision-date 2013-07-15;
    }

    organization
        "Travelping GmbH";

    contact
        "Röntgenstraße 13
        39108 Magdeburg
        Editor: Helge Sychla <hs@travelping.com>";

    description
        "This module defines RPCs for the TeraStream home gateway project.";

    revision "2013-12-12" {
        description
            "Version 0.1.0 -- Initial version.";
    }

    // feature statements

    // identity statements

    // typedef statements

    // grouping statements

    grouping fw-status {
        leaf status {
            type enumeration {
                enum planned;
                enum in-progress;
                enum done;
            }
        }
        leaf percent {
            when "hg-fw-mgmt:status = 'in-progress'";
            type int32 {
                range "0..100";
            }
        }
    }


    // data definition statements

    // augment statements

    // rpc statements

    rpc system-reset {
        description
            "Requests the device to delete the startup configuration and perform a reboot.";
    }

    rpc firmware-download {
        input {
            choice transport {
                description
                    "Protocol used for the firmware download";
                case ftp {
                    container ftp {
                        presence true;
                        leaf address {
                            type inet:host;
                            mandatory true;
                            description 
                                "Address if the firmware update";
                        }
                    }
                }
                case http {
                    container http {
                        presence true;
                        leaf address {
                            type inet:host;
                            description
                                "Address if the firmware update";
                        }
                    }
                }
            }
        }
        output {
            leaf job-id {
                type int32;
                mandatory true;
            }
        }
    }

    rpc firmware-commit {
        description
            "Install a previously donwloaded firmware.";
        input {
            leaf job-id {
                type int32;
                mandatory true;
            }
        }
    }

    rpc firmware-status {
        description
            "Status of a firmware download or commit.";
        input {
            leaf job-id {
                type int32;
                mandatory true;
            }
        }
        output {
            leaf job-id {
                type int32;
                mandatory true;
            }
            choice task {
                case download {
                    container download {
                        presence true;
                        uses fw-status;
                    }
                }
                case commit {
                    container commit {
                        presence true;
                        uses fw-status;
                    }
                }
            }
        }
    }

    // This will also need a config node somewhere! 
    rpc set-active-partition {
        description
            "Sets the partition that that will be active after next boot.";
        input {
            leaf partition-id {
                type uint8;
                mandatory true;
            }
        }
    }

    // notification statements

    // DO NOT put deviation statements in a published module
}
