module homegateway-system {

 namespace "urn:homegateway:system";

 prefix "hgs";

 // import statements here: e.g.,

 import ietf-system {
  prefix "sys";
  revision-date 2013-11-07;
 }

 organization
 "Travelping GmbH";

 contact
  "Röntgenstraße 13
  39108 Magdeburg
  Editor: Helge Sychla <hs@travelping.com>";

 description
  "This module defines a home gateway for the TeraStream project.";

 revision "2013-12-12" {
   description
     "Version 0.1.0 -- Move augmentations from homegateway to separate module.";
 }

 // deviate statements

 // feature statements

 // identity statements

 // typedef statements

 // grouping statements

 // data definition statements

 // augment statements

 augment "/sys:system-state/sys:platform" {
   leaf serial-number {
     type string;
     description
       "Serial Number of the device";
   }
 }

 augment "/sys:system-state/sys:platform" {
   leaf firmware-version {
     type string;
     description
       "Version of the currently running firmware";
   }
 }

 // rpc statements

 // notification statements

 // DO NOT put deviation statements in a published module
}
