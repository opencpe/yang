module homegateway {

 namespace "urn:homegateway";

 prefix "hg";

 // import statements here: e.g.,

 organization
 "Travelping GmbH";

 contact
  "Röntgenstraße 13
  39108 Magdeburg
  Editor: Helge Sychla <hs@travelping.com>";

 description
  "This module defines a home gateway for the TeraStream project.";

 revision "2013-12-12" {
   description
     "Version 0.1.1 -- Implementation of 0.1.0-review";
 }
 revision "2013-12-03" {
   description
     "Version 0.1.0 -- Initial version with IETF data models";
 }

 // deviate statements

 // feature statements

 // identity statements

 // typedef statements

 // grouping statements

 // data definition statements

 // augment statements

 // rpc statements

 // notification statements

 // DO NOT put deviation statements in a published module
}
