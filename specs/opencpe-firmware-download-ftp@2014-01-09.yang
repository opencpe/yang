module opencpe-firmware-download-ftp {

    namespace "urn:opencpe:firmware-dl-ftp";

    prefix "ocpe-fw-dl-ftp";

    // import statements here: e.g.,

    import ietf-inet-types {
        prefix "inet";
        revision-date 2013-07-15;
    }

    organization
        "Travelping GmbH";

    contact
        "Röntgenstraße 13
        39108 Magdeburg
        Editor: Helge Sychla <hs@travelping.com>";

    description
        "This module defines RPCs firmware downloads using FTP.";

    revision "2014-01-09" {
        description
            "Version 0.1.0 -- Initial version.";
    }

    // feature statements

    feature firmware-slots {
        description
            "Indicates that this device can store more than one firmware version 
            which can be selectively booted.";
    }

    // identity statements

    // typedef statements

    // grouping statements

    grouping fw-status {
        leaf status {
            type enumeration {
                enum planned;
                enum in-progress;
                enum done;
            }
        }
        leaf percent {
            when "ocpe-fw-dl-ftp:status = 'in-progress'";
            type int32 {
                range "0..100";
            }
        }
    }


    // data definition statements

    // augment statements

    // rpc statements

    rpc firmware-download-ftp {
        input {
            leaf address {
                type inet:uri;
                mandatory true;
                description 
                    "Address of the firmware update";
            }
            choice credentials {
                description
                    "Type of authentication to use for firmware downloads.";

                case user-pass {
                    container user-pass {
                        presence true;
                        leaf username {
                            type string;
                        }
                        leaf password {
                            type string;
                        }
                    }
                }
                case certificate {
                    container certificate {
                        presence true;
                        leaf path {
                            type string;
                        }
                    }
                }
            }

            leaf download-target {
                if-feature firmware-slots;

                description
                    "Name of the firmware-slot in which the downloaded firmware will be installed.";
                type string;
            }
        }
        output {
            leaf job-id {
                type int32;
                mandatory true;
            }
        }
    }

    // notification statements

    // DO NOT put deviation statements in a published module
}
