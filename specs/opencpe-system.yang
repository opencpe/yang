module opencpe-system {
    namespace "urn:telekom:opencpe:system";

    prefix "opencpe";

    import ietf-inet-types {
        prefix "inet";
    }

    import Device.DeviceInfo {
        prefix DevInf;
    }

    organization "Deutsche Telekom AG";

    contact 
        'Web:   <http://opencpe.org/contact>
Email: OpenCPE Support
       <mailto:support@opencpe.org>';

    description
        'Copyright (c) 2013 Deutsche Telekom AG

This module defines system querying and manipulation interfaces of the OpenCPE platform.
';

    revision "2013-09-22" {
        description "Version 0.1.0 -- Initial release";
    }

    // extension statements
    // feature statements
    // identity statements
    // typedef statements

    // grouping statements
    grouping os-version-info {
        leaf KernelName {
            description 'Kernel name';
            type string;
            mandatory true;
        }
        leaf NodeName {
            description 'Network node hostname';
            type string;
            mandatory true;
        }
        leaf KernelRelease {
            description 'Kernel release';
            type string;
            mandatory true;
        }
        leaf KernelVersion {
            description 'Kernel version';
            type string;
            mandatory true;
        }
        leaf MachineArchitecture {
            description 'machine hardware name';
            type string;
            mandatory true;
        }
        leaf ProcessorType {
            description 'Processor type, might be "unknown"';
            type string;
            mandatory true;
        }
        leaf HardwarePlatform {
            description 'Hardware platform, might be "unknown"';
            type string;
            mandatory true;
        }
        leaf OperatingSystem {
            description 'Operating system name';
            type string;
            mandatory true;
        }
    }

    grouping upgrade-info {
        leaf FirmwareUri {
            description 'TODO';
            type inet:uri;
            mandatory true;
        }
        leaf TimeslotOffset {
            description 'TODO';
            type uint16;
            mandatory false;
            units minutes;
        }
        leaf TimeslotDuration {
            description 'TODO';
            type uint16;
            mandatory false;
            units minutes;
        }
    }

    grouping system-info {
        leaf SystemId {
            description 'TODO';
            type string;
            mandatory true;
        }
    }

    container SystemState {
        description "Holds the system's state.";
        container OsVersionInformation{
            config false;
            description 'Holds information about the underlying OS';
            uses os-version-info;
        }
        container UpgradeInformation {
            config false;
            description 'Holds information about planned firmware upgrades';
            uses upgrade-info;
        }
        container SystemInformation {
            description 'Holds information about the device';
            uses system-info;
        }
        container DeviceInfo {
            description 'TR-181 DeviceInfo Data Model';
            uses DevInf:DeviceInfo;
        }
    }

    // rpc statements

    rpc GetOsVersionInfo {
        description 'Returns information about the underlying OS';
        output {
            uses os-version-info;
        }
    }

    rpc UpgradeFirmware {
        description 'Instructs the device to perform a firmware upgrade';
        input {
            uses upgrade-info;
        }
    }

    rpc GetSystemInfo {
        description 'Returns information about the device';
        output {
            uses system-info;
            uses DevInf:DeviceInfo;
        }
    }

    // notification statements
}
